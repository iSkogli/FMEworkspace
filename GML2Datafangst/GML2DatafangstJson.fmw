FME workspace GML2DatafangstJson.fmw

Parameters:
- Datafangst_Kontraktsid = 0e1d86dc-b2ca-4803-a13f-a90642f94852
- GML-fil = C:\DATA\Git\jetgeo\GLA\Data\501\Belysningstrekning_Kabel_Lillehammer.gml
- Datafangst_user = ingasko@hotmail.com   # HTTP Authentication Username
- Datafangst_pwd =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   # HTTP Authentication Password
- Dataområde = $(FME_MF_DIR)Data

Note: Parametre / GML-fil: / Fila som skal leses inn i datafangst. / Datafangst_kontraktsid: / Kontrakt må opprettes i Datafangst-applikasjonen. / Datafangst_user / Datafangst_pwd: / Brukernavn / Passord for bruker i Datafangst. Må opprettes i Datafangst-applikasjonen. For SVV-ansatte Windows autentisering.
Creator
    GEOMTYPE = Geometry Object
    NUM = 1
    CREATED -> FeatureReader_GML [INITIATOR]
FeatureReader_GML
    ATTRS_TO_EXPOSE = fme_feature_type
    ATTR_ACCUM_MODE = Only Use Result
    COMBINE_GEOM = Use Result
    DATASET = $(GML-fil)
    FORMAT = GML
    GML_CACHE_XSD = yes
    GML_CONTINUE_ON_GEOM_ERROR = yes
    GML_ENFORCE_PATH_CONTINUITY_BY = SNAPPING_END_POINTS
    GML_EXPLORE_XSD_VALUES = NO
    GML_FEATURE_TYPES_SCHEMA_MODE = XML_SCHEMA
    GML_FLATTEN_XML_FRAGMENTS = NO
    GML_GML_EXPOSE_FORMAT_ATTRS = fme_feature_type,xml_char(50)
    GML_IGNORE_APPLICATON_SCHEMA = yes
    GML_MAP_ALL_SUBSTITUTABLE_PROPERTIES = YES
    GML_MULTI_VALUE_SIMPLE_PROPERTIES_AS_CSV = no
    GML_REPROJECT_DISPARATE_CRS_IN_MULTIPLE_GEOMETRIES = yes
    GML_USE_OLD_READER = NO
    GML_USE_SEARCH_ENVELOPE = NO
    GML_VALIDATE_DATASET = no
    INTERACT = <No Spatial Filter>
    OUTPUT_FEATURES_DISPLAY = Schema and Data Features
    <OTHER> -> AttributeCreator
    <OTHER> -> Junction_2 [off]
Junction_2
    -> PythonCaller
Junction
    -> AttributeCreator_2
    -> AttributeExploder

Bookmark: Mapping til Datakatalog-IDer - csv
AttributeCreator
    ATTR_TABLE = SET_TO tag = @Value(fme_feature_type)
    -> SchemaMapper_2
Note: Mapper objekttypenavn til VOT-ID vha mappingtabell ftMapping
SchemaMapper_2
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = number,4,0,char,20,
    CSV__SCHEMA_WITH_COL_NAMES = ftid,number,4,0,name,char,20,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = http://rdf.vegdata.no/nvdb/NVDB_ftMapping.csv
    FORMAT = CSV
    IDXDESTATTR = fme_feature_type
    IDXDESTCOL = ftid
    IDXSOURCEATTR = fme_feature_type
    IDXSOURCECOL = name
    ROW_ID_ATTR = _schemamapper_row_ids
    TABLE = CSV
    MAPPED -> SchemaMapper_3
Note: Mapper egenskapsnavn til ET-ID vha mappingtabell ptMapping
SchemaMapper_3
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = char,17,,number,4,0,number,6,0,char,43,
    CSV__SCHEMA_WITH_COL_NAMES = ft_attr,char,17,,ftid,number,4,0,ptid,number,6,0,name,char,43,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = http://rdf.vegdata.no/nvdb/NVDB_ptMapping.csv
    FORMAT = CSV
    IDXDESTATTR = fme_feature_type
    IDXDESTCOL = ""
    IDXSOURCEATTR = fme_feature_type
    IDXSOURCECOL = ""
    MAP_ATTRS = name ptid $(FME_ASC_16)
    MATCH_ATTRS = ft_attr ftid
    ROW_ID_ATTR = _schemamapper_row_ids
    TABLE = CSV
    MAPPED -> SchemaMapper_4
Note: Oversetter tillatte verdier til NVDB-tekstverdier
SchemaMapper_4
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = number,6,0,number,6,0,char,29,,char,34,
    CSV__SCHEMA_WITH_COL_NAMES = ptid,number,6,0,enid,number,6,0,name,char,29,,fullname,char,34,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = http://rdf.vegdata.no/nvdb/NVDB_enMapping.csv
    FORMAT = CSV
    IDXDESTATTR = fme_feature_type
    IDXDESTCOL = ""
    IDXSOURCEATTR = fme_feature_type
    IDXSOURCECOL = ""
    MAP_ATTRS = """""" ptid fullname
    MATCH_ATTRS = ptid name
    ROW_ID_ATTR = _schemamapper_row_ids
    TABLE = CSV
    MAPPED -> Counter
Counter
    CNT_ATTR = _count
    DOMAIN = counter
    SCOPE = Global
    START = 0
    -> Junction

Bookmark: Mapping til Datakatalog-IDer - sparql
PythonCaller
    PYTHONSOURCE:
      import fme
      import fmeobjects
      import http.client, urllib.parse
      import xml.etree.ElementTree as ET
      from urllib.parse import unquote
      #https://docs.python.org/3/library/xml.etree.elementtree.html#elementtree-parsing-xml

      def queryref():
              streng = "PREFIX rdfs: <http://www.w3.org/2000/01/rdf-schema#>" + \
                       "PREFIX owl: <http://www.w3.org/2002/07/owl#>" + \
                       "prefix onto:<http://www.ontotext.com/>" + \
                       "PREFIX uni: <http://rdf.vegdata.no/nvdb/nvdb_gml_mapping#>"
              return streng
      def queryft(name_ft):
              streng = queryref() + \
                       "select ?ft_mapping ?ftid ?name_ft where" + \
                       "{" + \
                       "?ft_mapping uni:ftid ?ftid . " + \
                       "?ft_mapping uni:name_ft ?name_ft ." + \
                       "?ft_mapping uni:name_ft '"+ name_ft +"'" + \
                       "}" + \
                       "&HTTP/1.1"
              return streng
      def querypt(ftid, name_pt):
              streng = queryref() + \
                       "select ?pt_mapping ?ptid ?ftid_pt ?name_pt where" + \
                       "{" + \
                       "?pt_mapping uni:ptid ?ptid . " + \
                       "?pt_mapping uni:ftid_pt "+ ftid +" . " + \
                       "?pt_mapping uni:ftid_pt ?ftid_pt ." + \
                       "?pt_mapping uni:name_pt ?name_pt ." + \
                       "?pt_mapping uni:name_pt '"+ name_pt +"'" + \
                       "}" + \
                       "&HTTP/1.1"
              return streng
      def queryen(ptid, name_en):
              streng = queryref() + \
                       "select ?en_mapping ?ptid_en ?enid ?name_en ?fullname_en where" + \
                       "{" + \
                       "?en_mapping uni:ptid_en ?ptid_en . " + \
                       "?en_mapping uni:ptid_en "+ str(ptid) +" . " + \
                       "?en_mapping uni:enid ?enid . " + \
                       "?en_mapping uni:name_en ?name_en ." + \
                       "?en_mapping uni:name_en '"+ str(name_en) +"' ." + \
                       "?en_mapping uni:fullname_en ?fullname_en" + \
                       "}" + \
                       "&HTTP/1.1"
              print(streng)
              return streng
      class FeatureProcessor(object):
          def __init__(self):
              pass
          def input(self,feature):
              headers = {"Content-type": "application/x-www-form-urlencoded","Accept": "application/sparql-results+xml"}
              conn = http.client.HTTPConnection("localhost",7200)
              ftOld=feature.getAttribute("fme_feature_type")
              print(ftOld)

              #Endre objekttypenavn
              conn.request("POST", "/repositories/nvdb", ("query="+queryft(ftOld)).encode('utf8'), headers)
              response = conn.getresponse()
              data = response.read()
              xmldata = ET.fromstring(data)
              ftNew=xmldata.find(".//*[@name='ftid']/{http://www.w3.org/2005/sparql-results#}literal").text
              feature.setAttribute("fme_feature_type", ftNew)

              #Endre egenskapsnavn
              for attr in feature.getAllAttributeNames():
                  if not attr.isnumeric():
                      ptOld=attr
                      conn.request("POST", "/repositories/nvdb", ("query="+querypt(ftNew, ptOld)).encode('utf8'), headers)
                      response = conn.getresponse()
                      data = response.read()
                      xmldata = ET.fromstring(data)
                      node=xmldata.find(".//*[@name='ptid']/{http://www.w3.org/2005/sparql-results#}literal")
                      if not node is None:
                          ptNew=node.text
                          #https://knowledge.safe.com/questions/104428/rename-feature-attribute-with-python.html
                          feature.performFunction('@RenameAttributes('+ptNew+','+ptOld+')')

                          #Endre egenskapsverdi
                          name_en=feature.getAttribute(ptNew)
                          print(ptNew)
                          print(name_en)
                          conn.request("POST", "/repositories/nvdb", ("query="+queryen(ptNew, name_en)).encode('utf8'), headers)
                          response = conn.getresponse()
                          print(response.status)
                          data = response.read()
                          print(data)
                          xmldata = ET.fromstring(data)
                          node=xmldata.find(".//*[@name='fullname_en']/{http://www.w3.org/2005/sparql-results#}literal")
                          print("node.text:")
                          if not node is None:
                              print(node.text)
                              enNew=node.text
                              feature.setAttribute(ptNew, enNew)
                              #https://knowledge.safe.com/questions/104428/rename-feature-attribute-with-python.html
                              #feature.performFunction('@RenameAttributes('+ptNew+','+ptOld+')')

              conn.close()
              self.pyoutput(feature)


          def close(self):
              pass
    PYTHONSYMBOL = FeatureProcessor
    -> Junction_3
Junction_3
    -> Junction

Bookmark: Flytter egenskaper til json-objekt "attributes"
AttributeCreator_2
    ATTR_TABLE:
      SET_TO typeId = @Value(fme_feature_type)
      SET_TO dataCatalogVersion = 2.20
    -> FeatureMerger [REQUESTOR]
AttributeExploder
    ATTR_NAME_LABEL = _attr_name
    ATTR_VALUE_LABEL = _attr_value
    EXPLODING_TYPE = Features
    KEEP_ATTRIBUTES = Yes
    KEEP_GEOMETRY = No
    -> Tester
Tester
    BOOL_OP = OR
    COMPOSITE_TEST = 1
    TEST_CLAUSE = NUM_TEST @Value(_attr_name) IN "xml_type","endringsflagg.Endringsflagg.tidspunktEndring","gml_id","fme_feature_type","fme_geometry","gml_original_coordinate_system","endringsflagg.Endringsflagg.typeEndring","_count","fme_type","tag","gml_parent_property","_schemamapper_row_ids","identifikasjon.Identifikasjon.lokalId","identifikasjon.Identifikasjon.navnerom","kvalitet.Posisjonskvalitet.målemetode","kvalitet.Posisjonskvalitet.nøyaktighet","kvalitet.Posisjonskvalitet.synbarhet"
    TEST_MODE = NUM_TEST
    FAILED -> StringConcatenator
StringConcatenator
    ACTION = Create New Attribute
    PARM_LINE = fme_basicstring:1%18%1%1%1%19%1:"@Value(_attr_name)":"@Value(_attr_value)"
    VAL_ATTR = _result
    -> ListBuilder
ListBuilder
    GROUP_BY = _count
    LIST_ATTRS_TO_INCLUDE = _result
    LIST_NAME = egenskaper
    -> ListConcatenator_2
ListConcatenator_2
    DROP_EMPTY_PARTS = No
    LIST_ATTR = egenskaper{}._result
    SEP = ,
    VAL_ATTR = attributes
    -> StringConcatenator_2
StringConcatenator_2
    ACTION = Overwrite Existing Attributes
    ATTRLIST = attributes
    PARM_LINE = fme_basicstring:1%18%1:{@Value(attributes)}
    -> FeatureMerger [SUPPLIER]

Bookmark: Datafangst input json
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> FeatureWriter [NewFeatureType]
FeatureWriter
    DATASET = $(Dataområde)\fme_feature_type.json
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_INDENT_SIZE = 0
    GEOJSON_MAX_COORDINATE_PRECISION = 10
    GEOJSON_PRETTY_PRINT = YES
    GEOJSON_STRICT_SPEC = Yes
    GEOJSON_WGS84_REPROJECTION = Yes
    GEOJSON_WRITER_CHARSET = UTF-8
    GEOJSON_WRITE_BOM = No
    TOTAL_FEATURES_WRITTEN_ATTR = _total_features_written
    SUMMARY -> JSONUpdater [DOCUMENT]
    SUMMARY -> JSONUpdater [UPDATE]
JSONUpdater
    JSON_FILE = $(Dataområde)\fme_feature_type.json
    JSON_TYPE = JSON File
    RESULT_ATTRIBUTE = _result
    UPDATE_TABLE = GENERATE_JSON_QUERY DELETE_FROM_OBJECT json name
    VISIBLE_QUERY_VALIDATE = No
    DOCUMENT -> HTTPCaller

Bookmark: Skriver til Datafangst
HTTPCaller
    AUTH_METHOD = Basic
    AUTH_PASSWORD = $(Datafangst_pwd)
    AUTH_USERNAME = $(Datafangst_user)
    CONNECTION_TIMEOUT_LENGTH = 60
    CUSTOM_HEADERS = accept;application/json Content-Type;application/geo+json
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = https://datafangst.kantega.no/api/v1/contract/$(Datafangst_Kontraktsid)/featurecollection
    TRANSFER_TIMEOUT_LENGTH = 90
    UPLOAD_BODY = @Value(_result)
    UPLOAD_TYPE = Specify Upload Body
    USE_COOKIES = No
    VERIFY_SSL_CERTIFICATES = Yes
    -> JSONExtractor

Bookmark: Dokumentasjon
JSONExtractor
    EXTRACT_QUERY_TABLE = AdresseStatus json["resources"][1]["src"]
    JSON_DOCUMENT = @Value(_response_body)
    READ_FROM_FILE = NO
    EVALUATED -> HTTPCaller_2
HTTPCaller_2
    AUTH_METHOD = Basic
    AUTH_PASSWORD = $(Datafangst_pwd)
    AUTH_USERNAME = $(Datafangst_user)
    CONNECTION_TIMEOUT_LENGTH = 60
    ERROR_ATTR = _error
    FILE_PATH_ATTR = _response_file_path
    FOLLOW_REDIRECTS = Yes
    HTTP_METHOD = GET
    OUTPUT_FILENAME = $(Dataområde)/DatafangstLogg.xml
    SAVE_FILE = File
    SAVE_MULTI = No
    STATUS_CODE_ATTR = _http_status_code
    TARGET_URL = @Value(AdresseStatus)
    TRANSFER_TIMEOUT_LENGTH = 90
    USE_COOKIES = No
    VERIFY_SSL_CERTIFICATES = Yes
