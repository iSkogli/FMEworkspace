FME workspace NVDB_ut_demo_midlertidig.fmw

Parameters:
- GeometrifilterJsonURL =
- GeometrifilterWKT =
- Geometrifilterbbox =
- Objekttyper =
- type_strukt =
- utFormat =
- utKoordSys =
- utSti =

Creator
    GEOMTYPE = Geometry Object
    NUM = 1
    CREATED -> NVDBAPI_les [Input_create]
Note: Lillehammer / https://www.norgeskart.no/ws/get-json.py?hash=Oc6JcHkB1BVmjWzlBFjs&save=true / Hamar / https://www.norgeskart.no/ws/get-json.py?hash=9svYxnwB8ZGuWLUTLMqj&save=true
NVDBAPI_les
    GeomatrifilterJsonURL = $(GeometrifilterJsonURL)
    Objekttyper = $(Objekttyper)
    type_strukt = sosinavn

FME custom transformer Transformer_2

Parameters:
- utKoordSys =

Tester_Input (input)
    -> Tester
Tester
    BOOL_OP = OR
    COMPOSITE_TEST = 1
    TEST_CLAUSE = TEST $(utKoordSys) = EPSG:25833
    TEST_MODE = TEST
    PASSED -> AttributeRemover
    FAILED -> Reprojector
Reprojector
    DEST = $(utKoordSys)
    INTERPOLATION_TYPE_NAME = Nearest Neighbor
    RASTER_CELL_SIZE = Preserve Cells
    RASTER_TOLERANCE = 0.0
    SOURCE = EPSG:25833
    REPROJECTED -> CoordinateSystemSetter_2
CoordinateSystemSetter_2
    COORDSYS = $(utKoordSys)
    -> AttributeRemover
AttributeRemover
    REMOVE_ATTRS = _clipped,_creation_instance,_part_number,gml_id,href,kommunenummer,geometri.wkt
    -> AttributeRemover_Output (output)
AttributeRemover_Output (output)

FME custom transformer NVDBAPIlesFilter

Parameters:
- AndreParametre =
- Objekttyper =
- Polygon =
- Vegkategori =
- Vegstatus =
- kartutsnitt =

Input (input)
    -> AttributeCreator_2
AttributeCreator_2
    ATTR_TABLE:
      SET_TO vegkategori = $(Vegkategori)
      SET_TO vegstatus = $(Vegstatus)
      SET_TO vegsystemreferanse
      SET_TO AndreParametre = FME_CONDITIONAL:DEFAULT_VALUE'_FME_NO_OP_'BOOL_OP;OR;COMPOSITE_TEST;1;TEST $(AndreParametre) != _FME_BLANK_STRING_'&$(AndreParametre)'FME_NUM_CONDITIONS2___
    -> PythonCaller
Junction_2
    -> Tester_2
Junction_3
    -> AttributeManager_8
AttributeCreator
    ATTR_TABLE = SET_TO href = https://nvdbapiles-v3.atlas.vegvesen.no/vegobjekter/@Value(_ftID)?inkluder=egenskaper,geometri,metadata@Value(kartutsnitt)@Value(vegsystemreferanse)@Value(AndreParametre)@Value(polygon)&srid=utm33
    -> AttributeRemover_2
AttributeRemover_2
    REMOVE_ATTRS = _element_index,_xmax,_xmin,_ymax,_ymin,_zmax,_zmin,AndreParametre,ftIDs,kartutsnitt,vegkategori,vegstatus,vegsystemreferanse
    -> Output_href (output)
Output_href (output)

Bookmark: Sett filter Vegsystemreferanse
PythonCaller
    PYTHONSOURCE:
      import fme
      import fmeobjects

      def processFeature(feature):
          vk=feature.getAttribute('vegkategori')
          vs=feature.getAttribute('vegstatus')
          if vk=='' and vs=='':
              feature.setAttribute('vegsystemreferanse','')
          else:
              if vs=='':
                  feature.setAttribute('vegsystemreferanse','&vegsystemreferanse='+vk.replace(' ', ','))
              else:
                  vsLi=list(vs.split(" "))
                  if vk=='':
                      vk="E R F K P S"
                  vkLi=list(vk.split(" "))
                  xy=""
                  for x in vkLi:
                      for y in vsLi:
                          xy=xy+','+x+y
                  vref='&vegsystemreferanse='+xy[1:]
                  #print('vegsystemreferanse: '+vref)
                  feature.setAttribute('vegsystemreferanse',vref)

          pass
    PYTHONSYMBOL = processFeature
    -> Tester

Bookmark: Sett filter kartutsnitt
Tester
    BOOL_OP = OR
    COMPOSITE_TEST = 1
    TEST_CLAUSE = TEST $(kartutsnitt) = ""
    TEST_MODE = TEST
    PASSED -> AttributeCreator_3
    FAILED -> AttributeCreator_4
AttributeCreator_3
    ATTR_TABLE = SET_TO kartutsnitt
    -> Junction_2
AttributeCreator_4
    ATTR_TABLE = SET_TO kartutsnitt = $(kartutsnitt)
    -> Junction_2

Bookmark: Sett filter kartutsnitt
Tester_2
    BOOL_OP = OR
    COMPOSITE_TEST = 1
    TEST_CLAUSE = TEST $(Polygon) = ""
    TEST_MODE = TEST
    PASSED -> AttributeCreator_5
    FAILED -> AttributeCreator_6
AttributeCreator_5
    ATTR_TABLE = SET_TO polygon
    -> Junction_3
AttributeCreator_6
    ATTR_TABLE = SET_TO polygon = $(Polygon)
    -> Junction_3

Bookmark: Objekttyper
AttributeManager_8
    ATTR_TABLE = SET_TO ftIDs = $(Objekttyper)
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> Junction
Junction
    -> AttributeCreator
AttributeManager_2 [off]
    ATTR_TABLE = SET_TO ftIDs = 821;105;813;591;606;100;822;573;856;607;107;923;924;721;595

FME custom transformer NVDBAPIlesFilterGeometriInn

Parameters:
- GeometrifilterJsonURL =
- GeometrifilterWKT =
- Geometrifilterbbox =

Input (input)
    -> Tester
Note: GeometrifilterJsonURL
Tester
    BOOL_OP = OR
    COMPOSITE_TEST = 1
    TEST_CLAUSE = TEST $(GeometrifilterJsonURL) != ""
    TEST_MODE = TEST
    PASSED -> FeatureReader [INITIATOR]
    FAILED -> Tester_2
Note: GeometrifilterWKT
Tester_2
    BOOL_OP = OR
    COMPOSITE_TEST = 1
    TEST_CLAUSE = TEST $(GeometrifilterWKT) != ""
    TEST_MODE = TEST
    PASSED -> GeometryReplacer
    FAILED -> Tester_3
GeometryReplacer
    KIND_LONG = OGC Well Known Text
    OGC_WKT_PRECISION_DISPLAY = 64-bit
    REMOVE_ATTRIBUTE = Yes
    SOURCE = $(GeometrifilterWKT)
    -> Junction_2
CoordinateExtractor_Output: Logger
    LOG_FEATURE = LOG_ONLY
    MAXCOORDS = 20
    MAXFEATS = 20
    MESSAGE = Feature is:
    SEVERITY = INFO
Note: Geometrifilterbbox
Tester_3
    BOOL_OP = OR
    COMPOSITE_TEST = 1
    TEST_CLAUSE = TEST $(Geometrifilterbbox) != ""
    TEST_MODE = TEST
    PASSED -> AttributeCreator_2
    FAILED -> Junction
AttributeCreator_2
    ATTR_TABLE = SET_TO kartutsnitt = $(Geometrifilterbbox)
    -> Junction
Junction
    -> Output (output)
Note: KlippegeometriWKT fra gitt kilde
Output (output)

Bookmark: Feometri - Json URL
FeatureReader
    ATTR_ACCUM_MODE = Only Use Result
    COMBINE_GEOM = Use Result
    DATASET = $(GeometrifilterJsonURL)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> Reprojector
Reprojector
    DEST = EPSG:25833
    INTERPOLATION_TYPE_NAME = Nearest Neighbor
    RASTER_CELL_SIZE = Preserve Cells
    RASTER_TOLERANCE = 0.0
    SOURCE = EPSG:4326
    REPROJECTED -> Junction_2

Bookmark: Utsnitt og klippegeometri
Junction_2
    -> AttributeRemover
AttributeRemover
    REMOVE_ATTRS = _xmax,_xmin,_ymax,_ymin,_zmax,_zmin
    -> GeometryExtractor
GeometryExtractor
    ATTR = KlippegeometriWKT
    KIND_LONG = OGC Well Known Text
    OGCVERSION = 1.2
    OGC_WKT_PRECISION_DISPLAY = 64-bit
    PREFER_POLYGON_OVER_SURFACE = No
    REMOVE_GEOMETRY = No
    -> AttributeCreator
AttributeCreator
    ATTR_TABLE = SET_TO Polygon = &polygon=@Substring(@Value(KlippegeometriWKT),10,@StringLength(@Value(KlippegeometriWKT))-12)
    -> CoordinateExtractor_Output
    -> Junction

FME custom transformer Transformer

Parameters:
- utKoordSys =

Tester_Input (input)
    -> Tester
Tester
    BOOL_OP = OR
    COMPOSITE_TEST = 1
    TEST_CLAUSE = TEST $(utKoordSys) = EPSG:25833
    TEST_MODE = TEST
    PASSED -> AttributeRemover
    FAILED -> Reprojector
Reprojector
    DEST = $(utKoordSys)
    INTERPOLATION_TYPE_NAME = Nearest Neighbor
    RASTER_CELL_SIZE = Preserve Cells
    RASTER_TOLERANCE = 0.0
    SOURCE = EPSG:25833
    REPROJECTED -> CoordinateSystemSetter_2
CoordinateSystemSetter_2
    COORDSYS = $(utKoordSys)
    -> AttributeRemover
AttributeRemover
    REMOVE_ATTRS = _clipped,_creation_instance,_part_number,gml_id,href,kommunenummer,geometri.wkt
    -> AttributeRemover_Output (output)
AttributeRemover_Output (output)

FME custom transformer NVDBAPIlesFilterGeometriInn_2

Parameters:
- GeometrifilterJsonURL =
- GeometrifilterWKT =
- Geometrifilterbbox =

Input (input)
    -> Tester
Note: GeometrifilterJsonURL
Tester
    BOOL_OP = OR
    COMPOSITE_TEST = 1
    TEST_CLAUSE = TEST $(GeometrifilterJsonURL) != ""
    TEST_MODE = TEST
    PASSED -> FeatureReader [INITIATOR]
    FAILED -> Tester_2
Note: GeometrifilterWKT
Tester_2
    BOOL_OP = OR
    COMPOSITE_TEST = 1
    TEST_CLAUSE = TEST $(GeometrifilterWKT) != ""
    TEST_MODE = TEST
    PASSED -> GeometryReplacer
    FAILED -> Tester_3
GeometryReplacer
    KIND_LONG = OGC Well Known Text
    OGC_WKT_PRECISION_DISPLAY = 64-bit
    REMOVE_ATTRIBUTE = Yes
    SOURCE = $(GeometrifilterWKT)
    -> Junction_2
CoordinateExtractor_Output: Logger
    LOG_FEATURE = LOG_ONLY
    MAXCOORDS = 20
    MAXFEATS = 20
    MESSAGE = Feature is:
    SEVERITY = INFO
Note: Geometrifilterbbox
Tester_3
    BOOL_OP = OR
    COMPOSITE_TEST = 1
    TEST_CLAUSE = TEST $(Geometrifilterbbox) != ""
    TEST_MODE = TEST
    PASSED -> AttributeCreator_2
    FAILED -> Junction
AttributeCreator_2
    ATTR_TABLE = SET_TO kartutsnitt = $(Geometrifilterbbox)
    -> Junction
Junction
    -> Output (output)
Note: KlippegeometriWKT fra gitt kilde
Output (output)

Bookmark: Feometri - Json URL
FeatureReader
    ATTR_ACCUM_MODE = Only Use Result
    COMBINE_GEOM = Use Result
    DATASET = $(GeometrifilterJsonURL)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> Reprojector
Reprojector
    DEST = EPSG:25833
    INTERPOLATION_TYPE_NAME = Nearest Neighbor
    RASTER_CELL_SIZE = Preserve Cells
    RASTER_TOLERANCE = 0.0
    SOURCE = EPSG:4326
    REPROJECTED -> Junction_2

Bookmark: Utsnitt og klippegeometri
Junction_2
    -> AttributeRemover
AttributeRemover
    REMOVE_ATTRS = _xmax,_xmin,_ymax,_ymin,_zmax,_zmin
    -> GeometryExtractor
GeometryExtractor
    ATTR = KlippegeometriWKT
    KIND_LONG = OGC Well Known Text
    OGCVERSION = 1.2
    OGC_WKT_PRECISION_DISPLAY = 64-bit
    PREFER_POLYGON_OVER_SURFACE = No
    REMOVE_GEOMETRY = No
    -> AttributeCreator
AttributeCreator
    ATTR_TABLE = SET_TO Polygon = &polygon=@Substring(@Value(KlippegeometriWKT),10,@StringLength(@Value(KlippegeometriWKT))-12)
    -> CoordinateExtractor_Output
    -> Junction

FME custom transformer NVDBAPI_les
Henter objekttyper fra NVDB les-API
Versjon av API: https://nvdbapiles-v3.atlas.vegvesen.no/
Input:
- Objekttper: Semikolon-separert list
- Andre filtre: Eksempel: kommune=3001,3002&overlapp=67
- Geometri json URL: Eksempel: https://www.norgeskart.no/ws/get-json.py?hash=Oc6JcHkB1BVmjWzlBFjs&save=true
- Geometri WKT: POLYGON((286793.02 6746649.26,287158.62 6746653.89,287150.7 6746448.6,286834.71 6746409.62,286793.02 6746649.26))
- Geometrifilter bbox:Eksempel: &kartutsnitt=286793,6746448,287150,6746649
Output:
- Fetures
Kilde: https://git.vegvesen.no/projects/FME/repos/nvdbapilesfelles/browse
Utviklet av Knut Jetlund og Ingar Skogli
Statens vegvesen september 2021

Parameters:
- AndreParametre =
- GeomatrifilterJsonURL =
- GeometrifilterWKT =
- Geometrifilterbbox =
- Objekttyper =
- Vegkategori =
- Vegstatus =
- type_strukt =

Note: Om workspacet / Henter objekttyper fra NVDB les-API / Versjon av API: https://nvdbapiles-v3.atlas.vegvesen.no/ / Input: / Se boks Input-parametre / Output: / NVDB features / Kilde: Kilde: https://git.vegvesen.no/projects/FME/repos/nvdbapilesfelles/browse / Utviklet av Knut Jetlund og Ingar Skogli / Statens vegvesen september 2021
Input_create (input)
    -> NVDBAPIlesFilterGeometriInn
NVDBAPIlesFilterGeometriInn
    GeometrifilterJsonURL = $(GeomatrifilterJsonURL)
    GeometrifilterWKT = $(GeometrifilterWKT)
    Geometrifilterbbox = $(Geometrifilterbbox)
    -> NVDBAPIlesFilter
NVDBAPIlesFilter
    AndreParametre = $(AndreParametre)
    Objekttyper = $(Objekttyper)
    Polygon = @Value(Polygon)
    Vegkategori = $(Vegkategori)
    Vegstatus = $(Vegstatus)
    kartutsnitt = @Value(kartutsnitt)
    Output_href -> NVDBAPIlesVegobjekter [Input_href]
Note: Input-parametre / Dokumentasjon NVDB les-API: / https://nvdbapiles-v3.atlas.vegvesen.no/dokumentasjon/openapi/#/Vegobjekter/get_vegobjekter__vegobjekttypeid_ / Parametre - eksempler/dokumentasjon/info: / Objekttper: / Leveranse prosjekt: 532;98;79;95 / Ledningsregistreringsforskriften: 77;79;83;92;852;853;939;843;882;80;208;209;82;78;844;876;85;210;828 / Elveg2.0: 923;924;105;721;821;538;813;591;606;100;822;595;573;856;607;107;532 / Andre filtre: / Eksempel: / kommune=3001,3002&overlapp=67 / Hamar = 3403 / Geometri / Geometri json URL: / Definer i Norgeskart.no (epsg-kode 4326) / Eksempel: https://www.norgeskart.no/ws/get-json.py?hash=Oc6JcHkB1BVmjWzlBFjs&save=true / Geometri WKT: / UTM sone 33 / Eksempel Hamar sentrum: / POLYGON((286793.02 6746649.26,287158.62 6746653.89,287150.7 6746448.6,286834.71 6746409.62,286793.02 6746649.26)) / For andre formater og koordinatsystemer, legg til transformere som kobler til denne. / Geometrifilter bbox: / Dokumentasjon: https://api.vegdata.no/parameter/lokasjonsfilter.html / UTM sone 33 / Eksempel Hamar sentrum: / &kartutsnitt=286793,6746448,287150,6746649
NVDBAPIlesVegobjekter
    NESTE.HREF = @Value(href)
    _FTID = @Value(_ftID)
    type_strukt = $(type_strukt)
    Output_feature -> Transformer [Tester_Input]
Transformer
    utKoordSys = EPSG:25833
    AttributeRemover_Output -> Output_NVDBfeatures (output)
Note: Oppslag mot NVDB skjer i UTM sone 33 fordi: / 1. APIet har ikke konsekvent angivelse av srid: utm32, 4623 / 2. APIet har ulik håndtering av rekkefølge på nord- og øst-korrdinat: / json Øst, Nord / wkt Øst, Nord / NVDB kall pol utm Øst, Nord / NVDB kall pol 4326 Nord, Øst / NVDB resultat Som kall / 3. FME støtter ikke koordsys som inkluderer norske høydreref?
Output_NVDBfeatures (output)

FME custom transformer NVDBAPIlesFilter_2

Parameters:
- AndreParametre =
- Objekttyper =
- Polygon =
- Vegkategori =
- Vegstatus =
- kartutsnitt =

Input (input)
    -> AttributeCreator_2
AttributeCreator_2
    ATTR_TABLE:
      SET_TO vegkategori = $(Vegkategori)
      SET_TO vegstatus = $(Vegstatus)
      SET_TO vegsystemreferanse
      SET_TO AndreParametre = FME_CONDITIONAL:DEFAULT_VALUE'_FME_NO_OP_'BOOL_OP;OR;COMPOSITE_TEST;1;TEST $(AndreParametre) != _FME_BLANK_STRING_'&$(AndreParametre)'FME_NUM_CONDITIONS2___
    -> PythonCaller
Junction_2
    -> Tester_2
Junction_3
    -> AttributeManager_8
AttributeCreator
    ATTR_TABLE = SET_TO href = https://nvdbapiles-v3.atlas.vegvesen.no/vegobjekter/@Value(_ftID)?inkluder=egenskaper,geometri,metadata@Value(kartutsnitt)@Value(vegsystemreferanse)@Value(AndreParametre)@Value(polygon)&srid=utm33
    -> AttributeRemover_2
AttributeRemover_2
    REMOVE_ATTRS = _element_index,_xmax,_xmin,_ymax,_ymin,_zmax,_zmin,AndreParametre,ftIDs,kartutsnitt,vegkategori,vegstatus,vegsystemreferanse
    -> Output_href (output)
Output_href (output)

Bookmark: Sett filter Vegsystemreferanse
PythonCaller
    PYTHONSOURCE:
      import fme
      import fmeobjects

      def processFeature(feature):
          vk=feature.getAttribute('vegkategori')
          vs=feature.getAttribute('vegstatus')
          if vk=='' and vs=='':
              feature.setAttribute('vegsystemreferanse','')
          else:
              if vs=='':
                  feature.setAttribute('vegsystemreferanse','&vegsystemreferanse='+vk.replace(' ', ','))
              else:
                  vsLi=list(vs.split(" "))
                  if vk=='':
                      vk="E R F K P S"
                  vkLi=list(vk.split(" "))
                  xy=""
                  for x in vkLi:
                      for y in vsLi:
                          xy=xy+','+x+y
                  vref='&vegsystemreferanse='+xy[1:]
                  #print('vegsystemreferanse: '+vref)
                  feature.setAttribute('vegsystemreferanse',vref)

          pass
    PYTHONSYMBOL = processFeature
    -> Tester

Bookmark: Sett filter kartutsnitt
Tester
    BOOL_OP = OR
    COMPOSITE_TEST = 1
    TEST_CLAUSE = TEST $(kartutsnitt) = ""
    TEST_MODE = TEST
    PASSED -> AttributeCreator_3
    FAILED -> AttributeCreator_4
AttributeCreator_3
    ATTR_TABLE = SET_TO kartutsnitt
    -> Junction_2
AttributeCreator_4
    ATTR_TABLE = SET_TO kartutsnitt = $(kartutsnitt)
    -> Junction_2

Bookmark: Sett filter kartutsnitt
Tester_2
    BOOL_OP = OR
    COMPOSITE_TEST = 1
    TEST_CLAUSE = TEST $(Polygon) = ""
    TEST_MODE = TEST
    PASSED -> AttributeCreator_5
    FAILED -> AttributeCreator_6
AttributeCreator_5
    ATTR_TABLE = SET_TO polygon
    -> Junction_3
AttributeCreator_6
    ATTR_TABLE = SET_TO polygon = $(Polygon)
    -> Junction_3

Bookmark: Objekttyper
AttributeManager_8
    ATTR_TABLE = SET_TO ftIDs = $(Objekttyper)
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> Junction
Junction
    -> AttributeCreator
AttributeManager_2 [off]
    ATTR_TABLE = SET_TO ftIDs = 821;105;813;591;606;100;822;573;856;607;107;923;924;721;595

FME custom transformer NVDBAPIlesVegobjekter
Leser NVDB API les.
Input: href
Output: NVDB API features

Parameters:
- NESTE.HREF =
- _FTID =
- type_strukt =

Note: Kan det defineres at et element SKAL blli en liste? Vil i så fall kunne forenkle koden i NVDBTranslator mye. / Se under cardinality under dokumentasjon i XML Fragmenter
Input_href (input)
    -> HTTPCaller_3
Loop (input)
    -> HTTPCaller_3
HTTPCaller_3
    CONNECTION_TIMEOUT_LENGTH = 60
    CUSTOM_HEADERS = Accept;application/vnd.vegvesen.nvdb-v3-rev1+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> AttributeRemover_2
    -> PythonCaller_3
Note: Slå opp objekttype
PythonCaller_3
    NEW_ATTRIBUTES = XMLObjekttype
    PYTHONSOURCE:
      import fme
      import fmeobjects
      from urllib.request import Request, urlopen
      import xml.etree.ElementTree as ET
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              ft=str(feature.getAttribute('_ftID'))
              url = "https://nvdbapiles-v3.atlas.vegvesen.no/vegobjekttyper/" + str(ft) + "?inkluder=egenskapstyper"
              req = Request(url)
              req.add_header('Accept', 'application/xml')
              content = urlopen(req).read()
              feature.setAttribute('XMLObjekttype', content)
              self.pyoutput(feature)
          def close(self):
              pass
    PYTHONSYMBOL = FeatureProcessor
    -> XMLFragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg kommunenummer startdato LinearLocationReference.networkReference{}.SimpleLinearReference.element.xlink_href LinearLocationReference.networkReference{}.SimplePointReference.element.xlink_href LinearLocationReference.networkReference{}.SimpleLinearReference.fromPosition.LR_DistanceExpression.distanceAlong LinearLocationReference.networkReference{}.SimpleLinearReference.toPosition.LR_DistanceExpression.distanceAlong LinearLocationReference.networkReference{}.SimplePointReference.atPosition.LR_DistanceExpression.distanceAlong LinearLocationReference.networkReference{}.SimpleLinearReference.fromPosition.LR_DistanceExpression.distanceAlong.uom LinearLocationReference.networkReference{}.SimpleLinearReference.toPosition.LR_DistanceExpression.distanceAlong.uom LinearLocationReference.networkReference{}.SimplePointReference.atPosition.LR_DistanceExpression.distanceAlong.uom LinearLocationReference.networkReference{}.SimpleLinearReference.applicableDirection LinearLocationReference.networkReference{}.SimplePointReference.applicableDirection
    PYTHONSOURCE:
      import fme
      import fmeobjects
      import xml.etree.ElementTree as ET

      def extractNVDB_XML(feature):

          ns='vegvesen.no.nvdb' # FME_MacroValues['namespace']
          #print('objektid: '+str(feature.getAttribute('id')))

           # Setter feature type
          if FME_MacroValues['type_strukt']=='sosinavn' or FME_MacroValues['utFormat']=='GML':

              tre = ET.fromstring(feature.getAttribute('XMLObjekttype'))
              e = tre.findall('sosinavn')
              for i in e:
                  ft = str(i.text)
          elif FME_MacroValues['type_strukt']=='navn':
              ft=str(feature.getAttribute('metadata.type.navn'))
          else:
              ft=str(feature.getAttribute('metadata.type.id'))


          #ft=str(feature.getAttribute('metadata.type.id'))


          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          #Geometri
          v=feature.getAttribute('geometri.wkt')
          if v != None:
              feature.setAttribute('geometri', v)
          feature.removeAttribute('geometri.wkt')
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')

          # Henter ut egenskaper
          i = 0
          sisteEgenskap=False
          while sisteEgenskap==False:

              if FME_MacroValues['type_strukt']=='sosinavn' or FME_MacroValues['utFormat']=='GML':
                  egenskapsid = feature.getAttribute('egenskaper.egenskap{%d}.id' % i)
                  tre = ET.fromstring(feature.getAttribute('XMLObjekttype'))
                  e = tre.findall('egenskapstyper/egenskapstype[id = "' + str(egenskapsid) + '"]/sosinavn')
                  funnet = False
                  for node in e:
                      n = node.text
                      funnet = True
                  if funnet == False:
                      n = egenskapsid
              elif FME_MacroValues['type_strukt']=='navn':
                  n = feature.getAttribute('egenskaper.egenskap{%d}.navn' % i)
              else:
                  n = feature.getAttribute('egenskaper.egenskap{%d}.id' % i)

              e = str(feature.getAttribute('egenskaper.egenskap{%d}.enum_id' % i))
              v = feature.getAttribute('egenskaper.egenskap{%d}.verdi' % i)
              #if v == None:
              #    if i==0:
              #        # 1. egenskap, ikke liste
              #        n = feature.getAttribute('egenskaper.egenskap.id')
              #        e = str(feature.getAttribute('egenskaper.egenskap.enum_id'))
              #        v = feature.getAttribute('egenskaper.egenskap.verdi')

              if n == None:
                  sisteEgenskap=True
              else:
                      if e == 'None' or FME_MacroValues['type_strukt']=='navn' or FME_MacroValues['type_strukt']=='sosinavn' or FME_MacroValues['utFormat']=='GML':
                          # if (n == 'Kommunenummer' and v == 0):
                          if v != None:
                              feature.setAttribute(n, v)
                              #print(str(n)+"="+str(v)+' (v), i:'+str(i))
                      else:
                          # Enumverdi for kodelisteverdier
                          feature.setAttribute(n, e)
                          #print(str(n)+"="+str(e)+' (e), i:'+str(i))
              i += 1
          #feature.removeAttribute('egenskaper.egenskap{}')
    PYTHONSYMBOL = extractNVDB_XML
    -> AttributeExposer_2
AttributeExposer_2
    ATTR_LIST = egenskaper.egenskap{}
    -> AttributeRemover
AttributeRemover
    LIST_ATTRS = egenskaper.egenskap{}
    -> GeometryReplacer
AttributeRemover_4
    LIST_ATTRS = _headers{} _headers{}.name _headers{}.value _hierarchy_child_id_list{}
    REMOVE_ATTRS = XMLObjekttype,_geometry_name,_headers{0}.name,_headers{0}.value,startdato,xml_fragment,xml_id,xml_matched_element,xml_parent_child_pos,xml_parent_id,_hierarchy_child_id_list{0},_hierarchy_id,_hierarchy_parent_id,_http_status_code,_url_contents,neste.href
    -> Output_feature (output)
Output_feature (output)
AttributeRemover_2
    LIST_ATTRS = _headers{}.name _headers{}.value
    REMOVE_ATTRS = _http_status_code,returnert,xml_fragment,xml_id,xml_matched_element,xml_parent_child_pos,xml_parent_id
    -> XMLFragmenter_2
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = returnert neste.href _ftID
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> AttributeRemover_3
AttributeRemover_3
    REMOVE_ATTRS = returnert,xml_fragment,xml_id,xml_matched_element,xml_parent_child_pos,xml_parent_id,_url_contents
    -> Loop (output)
Loop (output)

Bookmark: Geometri
GeometryReplacer
    KIND_LONG = OGC Well Known Text
    OGC_WKT_PRECISION_DISPLAY = 64-bit
    REMOVE_ATTRIBUTE = Yes
    SOURCE = @Value(geometri)
    -> 3DForcer
3DForcer
    KEEPZVAL = Yes
    ZVALATTR = NaN
    -> CoordinateSystemSetter_3
CoordinateSystemSetter_3
    COORDSYS = EPSG:25833
    -> Deaggregator

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> AttributeRemover_4

FME custom transformer NVDBAPIlesVegobjekter_2
Leser NVDB API les.
Input: href
Output: NVDB API features

Parameters:
- NESTE.HREF =
- _FTID =
- type_strukt =

Note: Kan det defineres at et element SKAL blli en liste? Vil i så fall kunne forenkle koden i NVDBTranslator mye. / Se under cardinality under dokumentasjon i XML Fragmenter
Input_href (input)
    -> HTTPCaller_3
Loop (input)
    -> HTTPCaller_3
HTTPCaller_3
    CONNECTION_TIMEOUT_LENGTH = 60
    CUSTOM_HEADERS = Accept;application/vnd.vegvesen.nvdb-v3-rev1+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> AttributeRemover_2
    -> PythonCaller_3
Note: Slå opp objekttype
PythonCaller_3
    NEW_ATTRIBUTES = XMLObjekttype
    PYTHONSOURCE:
      import fme
      import fmeobjects
      from urllib.request import Request, urlopen
      import xml.etree.ElementTree as ET
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              ft=str(feature.getAttribute('_ftID'))
              url = "https://nvdbapiles-v3.atlas.vegvesen.no/vegobjekttyper/" + str(ft) + "?inkluder=egenskapstyper"
              req = Request(url)
              req.add_header('Accept', 'application/xml')
              content = urlopen(req).read()
              feature.setAttribute('XMLObjekttype', content)
              self.pyoutput(feature)
          def close(self):
              pass
    PYTHONSYMBOL = FeatureProcessor
    -> XMLFragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg kommunenummer startdato LinearLocationReference.networkReference{}.SimpleLinearReference.element.xlink_href LinearLocationReference.networkReference{}.SimplePointReference.element.xlink_href LinearLocationReference.networkReference{}.SimpleLinearReference.fromPosition.LR_DistanceExpression.distanceAlong LinearLocationReference.networkReference{}.SimpleLinearReference.toPosition.LR_DistanceExpression.distanceAlong LinearLocationReference.networkReference{}.SimplePointReference.atPosition.LR_DistanceExpression.distanceAlong LinearLocationReference.networkReference{}.SimpleLinearReference.fromPosition.LR_DistanceExpression.distanceAlong.uom LinearLocationReference.networkReference{}.SimpleLinearReference.toPosition.LR_DistanceExpression.distanceAlong.uom LinearLocationReference.networkReference{}.SimplePointReference.atPosition.LR_DistanceExpression.distanceAlong.uom LinearLocationReference.networkReference{}.SimpleLinearReference.applicableDirection LinearLocationReference.networkReference{}.SimplePointReference.applicableDirection
    PYTHONSOURCE:
      import fme
      import fmeobjects
      import xml.etree.ElementTree as ET

      def extractNVDB_XML(feature):

          ns='vegvesen.no.nvdb' # FME_MacroValues['namespace']
          #print('objektid: '+str(feature.getAttribute('id')))

           # Setter feature type
          if FME_MacroValues['type_strukt']=='sosinavn' or FME_MacroValues['utFormat']=='GML':

              tre = ET.fromstring(feature.getAttribute('XMLObjekttype'))
              e = tre.findall('sosinavn')
              for i in e:
                  ft = str(i.text)
          elif FME_MacroValues['type_strukt']=='navn':
              ft=str(feature.getAttribute('metadata.type.navn'))
          else:
              ft=str(feature.getAttribute('metadata.type.id'))


          #ft=str(feature.getAttribute('metadata.type.id'))


          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          #Geometri
          v=feature.getAttribute('geometri.wkt')
          if v != None:
              feature.setAttribute('geometri', v)
          feature.removeAttribute('geometri.wkt')
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')

          # Henter ut egenskaper
          i = 0
          sisteEgenskap=False
          while sisteEgenskap==False:

              if FME_MacroValues['type_strukt']=='sosinavn' or FME_MacroValues['utFormat']=='GML':
                  egenskapsid = feature.getAttribute('egenskaper.egenskap{%d}.id' % i)
                  tre = ET.fromstring(feature.getAttribute('XMLObjekttype'))
                  e = tre.findall('egenskapstyper/egenskapstype[id = "' + str(egenskapsid) + '"]/sosinavn')
                  funnet = False
                  for node in e:
                      n = node.text
                      funnet = True
                  if funnet == False:
                      n = egenskapsid
              elif FME_MacroValues['type_strukt']=='navn':
                  n = feature.getAttribute('egenskaper.egenskap{%d}.navn' % i)
              else:
                  n = feature.getAttribute('egenskaper.egenskap{%d}.id' % i)

              e = str(feature.getAttribute('egenskaper.egenskap{%d}.enum_id' % i))
              v = feature.getAttribute('egenskaper.egenskap{%d}.verdi' % i)
              #if v == None:
              #    if i==0:
              #        # 1. egenskap, ikke liste
              #        n = feature.getAttribute('egenskaper.egenskap.id')
              #        e = str(feature.getAttribute('egenskaper.egenskap.enum_id'))
              #        v = feature.getAttribute('egenskaper.egenskap.verdi')

              if n == None:
                  sisteEgenskap=True
              else:
                      if e == 'None' or FME_MacroValues['type_strukt']=='navn' or FME_MacroValues['type_strukt']=='sosinavn' or FME_MacroValues['utFormat']=='GML':
                          # if (n == 'Kommunenummer' and v == 0):
                          if v != None:
                              feature.setAttribute(n, v)
                              #print(str(n)+"="+str(v)+' (v), i:'+str(i))
                      else:
                          # Enumverdi for kodelisteverdier
                          feature.setAttribute(n, e)
                          #print(str(n)+"="+str(e)+' (e), i:'+str(i))
              i += 1
          #feature.removeAttribute('egenskaper.egenskap{}')
    PYTHONSYMBOL = extractNVDB_XML
    -> AttributeExposer_2
AttributeExposer_2
    ATTR_LIST = egenskaper.egenskap{}
    -> AttributeRemover
AttributeRemover
    LIST_ATTRS = egenskaper.egenskap{}
    -> GeometryReplacer
AttributeRemover_4
    LIST_ATTRS = _headers{} _headers{}.name _headers{}.value _hierarchy_child_id_list{}
    REMOVE_ATTRS = XMLObjekttype,_geometry_name,_headers{0}.name,_headers{0}.value,startdato,xml_fragment,xml_id,xml_matched_element,xml_parent_child_pos,xml_parent_id,_hierarchy_child_id_list{0},_hierarchy_id,_hierarchy_parent_id,_http_status_code,_url_contents,neste.href
    -> Output_feature (output)
Output_feature (output)
AttributeRemover_2
    LIST_ATTRS = _headers{}.name _headers{}.value
    REMOVE_ATTRS = _http_status_code,returnert,xml_fragment,xml_id,xml_matched_element,xml_parent_child_pos,xml_parent_id
    -> XMLFragmenter_2
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = returnert neste.href _ftID
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> AttributeRemover_3
AttributeRemover_3
    REMOVE_ATTRS = returnert,xml_fragment,xml_id,xml_matched_element,xml_parent_child_pos,xml_parent_id,_url_contents
    -> Loop (output)
Loop (output)

Bookmark: Geometri
GeometryReplacer
    KIND_LONG = OGC Well Known Text
    OGC_WKT_PRECISION_DISPLAY = 64-bit
    REMOVE_ATTRIBUTE = Yes
    SOURCE = @Value(geometri)
    -> 3DForcer
3DForcer
    KEEPZVAL = Yes
    ZVALATTR = NaN
    -> CoordinateSystemSetter_3
CoordinateSystemSetter_3
    COORDSYS = EPSG:25833
    -> Deaggregator

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> AttributeRemover_4
