FME workspace GML_NVDB2SOSIledning.fmw

Parameters:
- Source_GML_NVDB_Trekkekum =   # Source GML NVDB Trekkekum
- Source_GML_NVDB_Kum =   # Source GML NVDB Kum
- Dest_GML_LednReg_Kumlokk =   # Destination GML Ledn.reg Kumlokk
- Dest_GML_LednReg_Kum =   # Destination GML_Ledn.reg Kum

Readers:
- GML_1: GML from $(Source_GML_NVDB_Kum)
- GML_2: GML from $(Source_GML_NVDB_Trekkekum)

Writers:
- GML_4: GML to $(Dest_GML_LednReg_Kum)
- GML_5: GML to $(Dest_GML_LednReg_Kumlokk)

Bookmark: Feature input - NVDB
Trekkekum (reader GML_2)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, sideposisjon xml_buffer, vegsystemreferanse.Vegsystemreferanse.vegsystem.DT_Vegsystem.vegkategori xml_buffer, vegsystemreferanse.Vegsystemreferanse.vegsystem.DT_Vegsystem.vegfase xml_buffer, vegsystemreferanse.Vegsystemreferanse.vegsystem.DT_Vegsystem.vegnummer xml_int64, vegsystemreferanse.Vegsystemreferanse.vegstrekning.DT_Vegsystem.vegkategori xml_buffer, vegsystemreferanse.Vegsystemreferanse.vegstrekning.DT_Vegsystem.vegfase xml_buffer, vegsystemreferanse.Vegsystemreferanse.vegstrekning.DT_Vegsystem.vegnummer xml_int64, vegsystemreferanse.Vegsystemreferanse.sideanlegg.DT_Sideanlegg.sideanleggsdel xml_int64, vegsystemreferanse.Vegsystemreferanse.sideanlegg.DT_Sideanlegg.fraMeter xml_int64, vegsystemreferanse.Vegsystemreferanse.sideanlegg.DT_Sideanlegg.tilMeter xml_int64, vegsystemreferanse.Vegsystemreferanse.kryssystem.DT_Kryssystem.kryssdel xml_int64, vegsystemreferanse.Vegsystemreferanse.kryssystem.DT_Kryssystem.fraMeter xml_int64, vegsystemreferanse.Vegsystemreferanse.kryssystem.DT_Kryssystem.tilMeter xml_int64, vegsystemreferanse.Vegsystemreferanse.vegsystemreferanseFraDato xml_date, vegsystemreferanse.Vegsystemreferanse.vegsystemreferanseTilDato xml_date,
      vegsystemreferanse.Vegsystemreferanse.referanseretning xml_buffer, kumform xml_buffer, plassering xml_buffer, materiale_Kum xml_buffer, materiale_Lokk xml_buffer, brannsikker xml_buffer, diameter_Ytre xml_real64, bredde_Ytre xml_real64, lengde_Ytre xml_real64, dybde_Ytre xml_real64, antallRør xml_int64, tilleggsinformasjon xml_buffer, etableringsår xml_int64, driftsmerking xml_buffer, produsent xml_buffer, produktnavn xml_buffer, arkivnummer xml_buffer, arkivreferanse xml_buffer, prosjektreferanse xml_buffer, FKB_ID xml_buffer, eier xml_buffer, eier_Navn xml_buffer, vedlikeholdsansvarlig xml_buffer, posisjon xml_geometry, lineærPosisjon{}.LineærPosisjonPunkt.lineærReferanseMetode xml_buffer, lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer,
      lineærPosisjon{}.LineærPosisjonPunkt.nettverkselement.xlink_role xml_buffer, lineærPosisjon{}.LineærPosisjonPunkt.nettverkselement.xlink_title xml_buffer, lineærPosisjon{}.LineærPosisjonPunkt.nettverkselement.owns xml_boolean, lineærPosisjon{}.LineærPosisjonPunkt.posisjon xml_real64, assosiertKommentar{}.owns xml_boolean, assosiertKommentar{}.nilReason xml_buffer, assosiertKommentar{}.gml_remoteSchema xml_buffer, assosiertKommentar{}.xlink_href xml_buffer, assosiertKommentar{}.xlink_role xml_buffer, assosiertKommentar{}.xlink_title xml_buffer, assosiertTilstandSkade_Punkt{}.owns xml_boolean, assosiertTilstandSkade_Punkt{}.nilReason xml_buffer, assosiertTilstandSkade_Punkt{}.gml_remoteSchema xml_buffer, assosiertTilstandSkade_Punkt{}.xlink_href xml_buffer, assosiertTilstandSkade_Punkt{}.xlink_role xml_buffer, assosiertTilstandSkade_Punkt{}.xlink_title xml_buffer, assosiertTilstandSkadeFU_Punkt{}.owns xml_boolean, assosiertTilstandSkadeFU_Punkt{}.nilReason xml_buffer, assosiertTilstandSkadeFU_Punkt{}.gml_remoteSchema xml_buffer, assosiertTilstandSkadeFU_Punkt{}.xlink_href xml_buffer, assosiertTilstandSkadeFU_Punkt{}.xlink_role xml_buffer, assosiertTilstandSkadeFU_Punkt{}.xlink_title xml_buffer, assosiertTunnelløp.owns xml_boolean, assosiertTunnelløp.nilReason xml_buffer, assosiertTunnelløp.gml_remoteSchema xml_buffer, assosiertTunnelløp.xlink_href xml_buffer, assosiertTunnelløp.xlink_role xml_buffer, assosiertTunnelløp.xlink_title xml_buffer, assosiertTunnelløpUtenTrafikk.owns xml_boolean, assosiertTunnelløpUtenTrafikk.nilReason xml_buffer,
      assosiertTunnelløpUtenTrafikk.gml_remoteSchema xml_buffer, assosiertTunnelløpUtenTrafikk.xlink_href xml_buffer, assosiertTunnelløpUtenTrafikk.xlink_role xml_buffer, assosiertTunnelløpUtenTrafikk.xlink_title xml_buffer, assosiertDokumentasjon{}.owns xml_boolean, assosiertDokumentasjon{}.nilReason xml_buffer, assosiertDokumentasjon{}.gml_remoteSchema xml_buffer, assosiertDokumentasjon{}.xlink_href xml_buffer, assosiertDokumentasjon{}.xlink_role xml_buffer, assosiertDokumentasjon{}.xlink_title xml_buffer
    -> AttributeCreator_2
Kum (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, sideposisjon xml_buffer, vegsystemreferanse.Vegsystemreferanse.vegsystem.DT_Vegsystem.vegkategori xml_buffer, vegsystemreferanse.Vegsystemreferanse.vegsystem.DT_Vegsystem.vegfase xml_buffer, vegsystemreferanse.Vegsystemreferanse.vegsystem.DT_Vegsystem.vegnummer xml_int64, vegsystemreferanse.Vegsystemreferanse.vegstrekning.DT_Vegsystem.vegkategori xml_buffer, vegsystemreferanse.Vegsystemreferanse.vegstrekning.DT_Vegsystem.vegfase xml_buffer, vegsystemreferanse.Vegsystemreferanse.vegstrekning.DT_Vegsystem.vegnummer xml_int64, vegsystemreferanse.Vegsystemreferanse.sideanlegg.DT_Sideanlegg.sideanleggsdel xml_int64, vegsystemreferanse.Vegsystemreferanse.sideanlegg.DT_Sideanlegg.fraMeter xml_int64, vegsystemreferanse.Vegsystemreferanse.sideanlegg.DT_Sideanlegg.tilMeter xml_int64, vegsystemreferanse.Vegsystemreferanse.kryssystem.DT_Kryssystem.kryssdel xml_int64, vegsystemreferanse.Vegsystemreferanse.kryssystem.DT_Kryssystem.fraMeter xml_int64, vegsystemreferanse.Vegsystemreferanse.kryssystem.DT_Kryssystem.tilMeter xml_int64, vegsystemreferanse.Vegsystemreferanse.vegsystemreferanseFraDato xml_date, vegsystemreferanse.Vegsystemreferanse.vegsystemreferanseTilDato xml_date,
      vegsystemreferanse.Vegsystemreferanse.referanseretning xml_buffer, type xml_buffer, bruksområde xml_buffer, materialtype xml_buffer, plassering xml_buffer, lokkRist_Type xml_buffer, spesiellBelegningRundtKum xml_buffer, diameter xml_real64, diameter_Åpning xml_real64, dybde xml_real64, dybdeTilUtløp xml_real64, bredde1_Firkantkum xml_real64, bredde2_Firkantkum xml_real64, avstandFraVegkant xml_real64, stige xml_buffer, harFlyteramme xml_buffer, avløp xml_buffer, dykker xml_buffer, oljeutskilling xml_buffer, antallRørInn xml_int64, antallHjelpesluker xml_int64, kumskjerm xml_buffer, oppslammingstid xml_buffer, inngårIDrenssystem xml_buffer, etableringsår xml_int64, driftsmerking xml_buffer, produsent xml_buffer, produktnavn xml_buffer, leverandør xml_buffer, tilleggsinformasjon xml_buffer,
      arkivreferanse xml_buffer, prosjektreferanse xml_buffer, FKB_ID xml_buffer, eier xml_buffer, eier_Navn xml_buffer, vedlikeholdsansvarlig xml_buffer, posisjon xml_geometry, lineærPosisjon{}.LineærPosisjonPunkt.lineærReferanseMetode xml_buffer, lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer, lineærPosisjon{}.LineærPosisjonPunkt.nettverkselement.xlink_role xml_buffer, lineærPosisjon{}.LineærPosisjonPunkt.nettverkselement.xlink_title xml_buffer, lineærPosisjon{}.LineærPosisjonPunkt.nettverkselement.owns xml_boolean, lineærPosisjon{}.LineærPosisjonPunkt.posisjon xml_real64, assosiertKommentar{}.owns xml_boolean, assosiertKommentar{}.nilReason xml_buffer, assosiertKommentar{}.gml_remoteSchema xml_buffer, assosiertKommentar{}.xlink_href xml_buffer, assosiertKommentar{}.xlink_role xml_buffer, assosiertKommentar{}.xlink_title xml_buffer, assosiertLukketRørgrøft.owns xml_boolean, assosiertLukketRørgrøft.nilReason xml_buffer, assosiertLukketRørgrøft.gml_remoteSchema xml_buffer, assosiertLukketRørgrøft.xlink_href xml_buffer, assosiertLukketRørgrøft.xlink_role xml_buffer, assosiertLukketRørgrøft.xlink_title xml_buffer, assosiertStikkrenneKulvert.owns xml_boolean,
      assosiertStikkrenneKulvert.nilReason xml_buffer, assosiertStikkrenneKulvert.gml_remoteSchema xml_buffer, assosiertStikkrenneKulvert.xlink_href xml_buffer, assosiertStikkrenneKulvert.xlink_role xml_buffer, assosiertStikkrenneKulvert.xlink_title xml_buffer, assosiertSystemobjekt{}.owns xml_boolean, assosiertSystemobjekt{}.nilReason xml_buffer, assosiertSystemobjekt{}.gml_remoteSchema xml_buffer, assosiertSystemobjekt{}.xlink_href xml_buffer, assosiertSystemobjekt{}.xlink_role xml_buffer, assosiertSystemobjekt{}.xlink_title xml_buffer, assosiertTilstandsgrad_Kum{}.owns xml_boolean, assosiertTilstandsgrad_Kum{}.nilReason xml_buffer, assosiertTilstandsgrad_Kum{}.gml_remoteSchema xml_buffer, assosiertTilstandsgrad_Kum{}.xlink_href xml_buffer, assosiertTilstandsgrad_Kum{}.xlink_role xml_buffer, assosiertTilstandsgrad_Kum{}.xlink_title xml_buffer, assosiertTilstandSkade_Punkt{}.owns xml_boolean, assosiertTilstandSkade_Punkt{}.nilReason xml_buffer, assosiertTilstandSkade_Punkt{}.gml_remoteSchema xml_buffer, assosiertTilstandSkade_Punkt{}.xlink_href xml_buffer, assosiertTilstandSkade_Punkt{}.xlink_role xml_buffer, assosiertTilstandSkade_Punkt{}.xlink_title xml_buffer, assosiertTilstandSkadeFU_Punkt{}.owns xml_boolean, assosiertTilstandSkadeFU_Punkt{}.nilReason xml_buffer, assosiertTilstandSkadeFU_Punkt{}.gml_remoteSchema xml_buffer, assosiertTilstandSkadeFU_Punkt{}.xlink_href xml_buffer, assosiertTilstandSkadeFU_Punkt{}.xlink_role xml_buffer, assosiertTilstandSkadeFU_Punkt{}.xlink_title xml_buffer, assosiertTunnelløp.owns xml_boolean,
      assosiertTunnelløp.nilReason xml_buffer, assosiertTunnelløp.gml_remoteSchema xml_buffer, assosiertTunnelløp.xlink_href xml_buffer, assosiertTunnelløp.xlink_role xml_buffer, assosiertTunnelløp.xlink_title xml_buffer, assosiertVannhåndteringsanlegg.owns xml_boolean, assosiertVannhåndteringsanlegg.nilReason xml_buffer, assosiertVannhåndteringsanlegg.gml_remoteSchema xml_buffer, assosiertVannhåndteringsanlegg.xlink_href xml_buffer, assosiertVannhåndteringsanlegg.xlink_role xml_buffer, assosiertVannhåndteringsanlegg.xlink_title xml_buffer, assosiertDokumentasjon{}.owns xml_boolean, assosiertDokumentasjon{}.nilReason xml_buffer, assosiertDokumentasjon{}.gml_remoteSchema xml_buffer, assosiertDokumentasjon{}.xlink_href xml_buffer, assosiertDokumentasjon{}.xlink_role xml_buffer, assosiertDokumentasjon{}.xlink_title xml_buffer
    -> AttributeCreator

Bookmark: Manipulation
AttributeCreator_2
    ATTR_TABLE:
      SET_TO ytreDiameter = @Value(diameter_Ytre)
      SET_TO ytreHøyde = @Value(dybde_Ytre)
    -> Junction
AttributeCreator
    ATTR_TABLE:
      SET_TO ytreDiameter = @Value(diameter)+0,15
      SET_TO ytreHøyde = @Value(dybde)
    -> Junction
Junction
    -> GeometryPropertySetter
    -> Kum (writer GML_4)
GeometryPropertySetter
    GEOM_NAME_FIELD = senterLokk
    OVERWRITE_CHOICE = Yes
    SETTYPE_PARAM = Geometry Name
    SET -> Tester_1
Note: ToDo: Flere egenskaper mangler
Tester_1
    BOOL_OP = OR
    COMPOSITE_TEST = 1
    TEST_CLAUSE = TEST @Value(lokkRist_Type) != Åpen
    TEST_MODE = TEST
    PASSED -> Kumlokk (writer GML_5)

Bookmark: Feature output - Ledningsregistreringsforskriften
Kumlokk (writer GML_5)
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, senterLokk xml_geometry, identifikasjon.Identifikasjon.lokalId xml_buffer, identifikasjon.Identifikasjon.navnerom xml_buffer, identifikasjon.Identifikasjon.versjonId xml_buffer, rist xml_buffer, kumlokkform xml_buffer, påTank.nilReason xml_buffer, påTank.gml_remoteSchema xml_buffer, påTank.xlink_href xml_buffer, påTank.xlink_role xml_buffer, påTank.xlink_title xml_buffer, påTank.owns xml_boolean, påKum.nilReason xml_buffer, påKum.gml_remoteSchema xml_buffer, påKum.xlink_href xml_buffer, påKum.xlink_role xml_buffer, påKum.xlink_title xml_buffer, påKum.owns xml_boolean
Kum (writer GML_4)
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, hovedbruk xml_buffer, ytreDiameter xml_real64, posisjon xml_geometry, omriss xml_geometry, ytreHøyde xml_real64

FME custom transformer Hub3DBufferer
[Previously named the 3DBufferer]
This transformer creates a 3D buffer around points, lines and polygons by a user provided radius/offset
Points are replaced with spheres with a user defined radius. 
Lines are replaced by a tubular buffer with a user defined radius with spherical elbows around lines and arcs. Paths and aggregate lines are handled appropriately. Any arcs are stroked.
Polygons are extruded above and below by the radius/offset value along the average normal vector. The edge can be rounded or flush. 
All other geometries are output untouched through the <REJECTED> port.
The transformer has four parameters:
    Buffer Radius: 
This parameter sets the tube radius.
    Output Geometry:
This parameter sets the output geometry. 
The default Fast Surface setting creates a composite surface of individual segment tubes and elbow spheres. This is creates a suitable external appearance for opaque rendering, but the internal surfaces are visible when transparency is applied.
The True Solids (slow) option creates a true merged solid from the segment tubes and vertex spheres that is suitable for transparent rendering. However, this option increases the processing time considerably, and should be used only if necessary. 
    Maximum Arc Stroking Deviation:
If the Maximum Deviation has a value greater than 0, then arcs are converted into lines such that the maximum distance between the lines and the arcs is not greater than the value specified. If the Maximum Deviation value is greater than the primary or secondary axis of the arc or ellipse, then the converted lines will have minimum number of edges possible. If the Maximum Deviation value is smaller than or equal to 0, then the value of the Stroke Maximum Deviation advanced setting set in the workspace is used. If both values are smaller than or equal to 0, then arcs are converted into lines using the Number of Interpolated Edges value of 0.
    Polygon Buffer Edges:
The default Rounded setting creates a rounded edge to the buffer solid, with a semi-circular section of the user definedBuffer Radius.
The solid produce by the Flush setting has an edge coincident to the original polygon when viwed along the normal vector. This method is faster than the Rounded and always produces a true solid.

Parameters:
- DIAMETER =   # Buffer Radius
- OUTPUT = Fast Surface   # "Fast Surface"%"True Solids (slow)" Output Geometry
- TOLERANCE_VAL = 0.0   # Maximum Arc Stroking Deviation
- EDGE = Rounded   # Polygon Buffer Edges

INPUT (input)
    -> Counter
Note: Set Line IDs
Counter
    CNT_ATTR = _line_id
    DOMAIN = line
    SCOPE = Local
    START = 0
    -> AggregateFilter
Note: Deaggregate Aggregates
AggregateFilter
    AGGREGATE -> Deaggregator
    NOT_AGGREGATE -> Tester_7
Deaggregator
    ATTR_ACCUM_MODE = Merge List Attributes
    ATTR_CONFLICT_RES = Use List Attribute Values
    EXPLODE_INSTANCES = No
    LIST_ATTR_MODE_LOOKUP = LEAN
    MODE = Flatten One Level
    SPLIT_COMPOSITES = No
    DEAGGREGATED -> Tester_7
Note: Force 2D to 3D
Tester_7
    BOOL_OP = OR
    TEST_CLAUSE = TEST @Dimension() = 3
    TEST_MODE = Automatic
    PASSED -> GeometryFilter
    FAILED -> 3DForcer_2
3DForcer_2
    KEEPZVAL = No
    ZVALATTR = 0
    -> GeometryFilter
GeometryFilter
    BREAK_AGG = No
    POINT -> CoordinateExtractor_3
    LINE -> ArcStroker
    ARC -> ArcStroker
    AREA -> AttributeCreator_6
    ELLIPSE -> ArcStroker_2
    TEXT -> Cloner
    RASTER -> Cloner
    POINTCLOUD -> Cloner
    SURFACE -> Cloner
    SOLID -> Cloner
    COLLECTION -> Cloner
    NULL -> Cloner
    INSTANCE -> Cloner
Note: Clean up attributes
AttributeRemover_9
    REMOVE_ATTRS = _line_id
    -> OUTPUT (output)
Note: Stroke Arcs
ArcStroker
    MAKE_POLY = No
    STROKE_CHOICE = Maximum Deviation
    TOLERANCE_VAL = $(TOLERANCE_VAL)
    STROKED -> MeasureGenerator
Cloner
    COPIES = 1
    COPYATT = _copynum
    COPY -> Cloner_2
Cloner_2
    COPIES = 1
    COPYATT = _copynum
    COPY -> AttributeRemover_10
Note: Clean up attributes
AttributeRemover_10
    REMOVE_ATTRS = _line_id,_copynum
    -> <REJECTED> (output)
<REJECTED> (output)
Note: Stroke Ellipses
ArcStroker_2
    MAKE_POLY = No
    STROKE_CHOICE = Maximum Deviation
    TOLERANCE_VAL = $(TOLERANCE_VAL)
    STROKED -> AttributeCreator_6
Note: Set polygon edge flag
AttributeCreator_6
    ATTR_LIST = _poly,1
    -> PythonCaller_2
    -> Tester_6
Note: Round Edges?
Tester_6
    BOOL_OP = OR
    TEST_CLAUSE = TEST $(EDGE) = Rounded
    TEST_MODE = Automatic
    PASSED -> GeometryCoercer_5
Note: Coerce polygon / boundary to line
GeometryCoercer_5
    KIND = fme_line
    COERCED -> Counter_3
Note: Create individual line ids
Counter_3
    CNT_ATTR = _seg_id
    DOMAIN = segment
    SCOPE = Global
    START = 0
    -> Extender
    -> Chopper
    -> CoordinateCounter
Clipper_3__REJECTED_: Junction
Note: Calculate polygon / average normal vector
PythonCaller_2
    NEW_ATTRIBUTES = _normal_x _normal_y _normal_z
    PYTHONSOURCE:
      import math
      import fmeobjects
      # Template Function interface:
      def calcNormal(feature):

          counter0 = 0
          coordCount = feature.numVertices() - 1

          normalX = 0
          normalY = 0
          normalZ = 0

          # loop through the coordinates and calculate surface normal of the triangle formed by the
          # the point, its predecessor and its successor.
          while counter0 < coordCount:

              # get test coordinate and the ones before and after
              before = (counter0 + (coordCount - 1)) % coordCount
              after = (counter0 + (coordCount + 1)) % coordCount
              coords0 = feature.getCoordinate(before)
              coords1 = feature.getCoordinate(counter0)
              coords2 = feature.getCoordinate(after)

              # calculate normal
              x1 = coords0[0]
              x2 = coords1[0]
              x3 = coords2[0]

              y1 = coords0[1]
              y2 = coords1[1]
              y3 = coords2[1]

              z1 = coords0[2]
              z2 = coords1[2]
              z3 = coords2[2]

              normalX = normalX + ((y2-y1) * (z3-z1) - (y3-y1) * (z2-z1))
              normalY = normalY + ((z2-z1) * (x3-x1) - (z3-z1) * (x2-x1))
              normalZ = normalZ + ((x2-x1) * (y3-y1) - (x3-x1) * (y2-y1))

              counter0 = counter0 + 1

          # normalize vector
          length = math.sqrt(normalX**2 + normalY**2 + normalZ**2)
          normalX = normalX / length
          normalY = normalY / length
          normalZ = normalZ / length

          # write normal to feature
          feature.setAttribute('_normal_x',normalX)
          feature.setAttribute('_normal_y',normalY)
          feature.setAttribute('_normal_z',normalZ)
    PYTHONSYMBOL = calcNormal
    -> 3DAffiner
Note: Offset by radius back along normal
3DAffiner
    A = 1
    B = 0
    C = 0
    D = -@Value(_normal_x)*$(DIAMETER)
    E = 0
    F = 1
    G = 0
    H = -@Value(_normal_y)*$(DIAMETER)
    I = 0
    J = 0
    K = 1
    L = -@Value(_normal_z)*$(DIAMETER)
    AFFINED -> Extruder_3
Note: Extrude by twice radius along vector
Extruder_3
    EXTRUSION_VECTOR_INPUT = Vector
    EXTRUSION_X = @Value(_normal_x)*$(DIAMETER)*2
    EXTRUSION_Y = @Value(_normal_y)*$(DIAMETER)*2
    EXTRUSION_Z = @Value(_normal_z)*$(DIAMETER)*2
    -> Aggregator
Note: Aggregate tubes and / spheres into multi-solid
Aggregator
    ACCUM_ATTRS_NAME = Yes
    AGGREGATE_TYPE = Homogeneous Collection (If Possible)
    GROUP_BY = _line_id fme_feature_type
    MODE = Assemble One Level
    ORDERED = No
    SEP = ,
    AGGREGATE -> Tester_3
Note: Do solid processing?
Tester_3
    BOOL_OP = OR
    TEST_CLAUSE = TEST $(OUTPUT) = Fast Surface
    TEST_MODE = Automatic
    PASSED -> GeometryCoercer_3
    FAILED -> Clipper [CLIPPER]
    FAILED -> BoundsExtractor
Note: Coerce into surfaces
GeometryCoercer_3
    KIND = fme_composite_surface
    COERCED -> AttributeRemover_6
Note: Clean up attributes
AttributeRemover_6
    REMOVE_ATTRS = _forward,_reverse,_extend,_clipped,_fme_no_clipper
    -> AttributeRemover_11
Note: Clean up attributes
AttributeRemover_11
    REMOVE_ATTRS = _line_id,_poly,_seg_id,_normal_x,_normal_y,_normal_z
    -> OUTPUT (output)
OUTPUT (output)

Bookmark: Point Spheres
Note: Extract coordinates
CoordinateExtractor_3
    IND = 0
    X_ATTR = vertex_x
    Y_ATTR = vertex_y
    Z_ATTR = vertex_z
    Z_DEFAULT = -9999
    -> AttributeCreator_5
Note: Create XML for Sphere
AttributeCreator_5
    ATTR_LIST =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
    -> GeometryReplacer_3
Note: Create geometry from XML
GeometryReplacer_3
    ATTR = _geometry
    KIND_LONG = FME XML
    -> AttributeRemover_8
Note: Remove XML
AttributeRemover_8
    REMOVE_ATTRS = _geometry
    -> Scaler_2
Note: Scale sphere to diameter
Scaler_2
    RASTER_SCALING = Extents
    SCALE_ORIGIN = 0,0
    TEXT_LOC_ONLY = Location and Size
    XSCALE = $(DIAMETER)
    YSCALE = $(DIAMETER)
    ZSCALE = $(DIAMETER)
    SCALED -> Offsetter_3
Note: Move Sphere to / vertex location
Offsetter_3
    XOFF = @Value(vertex_x)
    YOFF = @Value(vertex_y)
    ZOFF = @Value(vertex_z)
    OFFSET -> AttributeRemover_7
Note: Clean up attributes
AttributeRemover_7
    REMOVE_ATTRS = vertex_x,vertex_y,vertex_z
    -> GeometryCoercer_4
Note: Coerce to brep solid
GeometryCoercer_4
    KIND = fme_brep_solid
    COERCED -> AttributeRemover_9

Bookmark: Generate distance measures
Note: Generate forward measure
MeasureGenerator
    DIM = 3
    MEASURE_NAME = forward
    MULT = 1
    -> Orientor
Note: Reverse line
Orientor
    KIND = REVERSE
    ORIENTED -> MeasureGenerator_2
Note: Generate reverse measure
MeasureGenerator_2
    DIM = 3
    MEASURE_NAME = reverse
    MULT = 1
    -> Orientor_2
Note: Reverse line again
Orientor_2
    KIND = REVERSE
    ORIENTED -> Counter_3

Bookmark: Vertex Spheres
Note: Count number of vertices
CoordinateCounter
    CNT_ATTR = _coordcount
    -> Chopper_2
Note: Chop into points
Chopper_2
    MAX_VERTICES = 1
    MODE = By Vertex
    REMNANT_ATTR = _remnant
    CHOPPED -> Counter_2
    UNTOUCHED -> Counter_2
Note: Number vertices
Counter_2
    CNT_ATTR = _coord
    DOMAIN = @Value(_seg_id)
    SCOPE = Global
    START = 1
    -> Tester
Note: Remove first and / last vertices
Tester
    BOOL_OP = COMPOSITE
    COMPOSITE_TEST = "1 AND 2 or 3"
    TEST_CLAUSE:
      TEST "@Value(_coord)" != "1"
      TEST "@Value(_coord)" != "@Value(_coordcount)"
      TEST "@Value(_poly)" = "1"
    TEST_MODE = Automatic
    PASSED -> CoordinateExtractor_2
Note: Extract coordinates
CoordinateExtractor_2
    IND = 0
    X_ATTR = vertex_x
    Y_ATTR = vertex_y
    Z_ATTR = vertex_z
    Z_DEFAULT = -9999
    -> MeasureExtractor
Note: Extract forward measure
MeasureExtractor
    GEOM_TYPE = Point
    MEASURE_ATTR = _forward
    MEASURE_NAME = forward
    -> MeasureExtractor_2
Note: Extract reverse measure
MeasureExtractor_2
    GEOM_TYPE = Point
    MEASURE_ATTR = _reverse
    MEASURE_NAME = reverse
    -> AttributeCreator_2
Note: Create XML for Sphere
AttributeCreator_2
    ATTR_LIST =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
    -> GeometryReplacer_2
Note: Create geometry from XML
GeometryReplacer_2
    ATTR = _geometry
    KIND_LONG = FME XML
    -> AttributeRemover_3
Note: Remove XML
AttributeRemover_3
    REMOVE_ATTRS = _geometry
    -> Scaler
Note: Scale sphere to diameter
Scaler
    RASTER_SCALING = Extents
    SCALE_ORIGIN = 0,0
    TEXT_LOC_ONLY = Location and Size
    XSCALE = $(DIAMETER)
    YSCALE = $(DIAMETER)
    ZSCALE = $(DIAMETER)
    SCALED -> Offsetter_2
Note: Move Sphere to / vertex location
Offsetter_2
    XOFF = @Value(vertex_x)
    YOFF = @Value(vertex_y)
    ZOFF = @Value(vertex_z)
    OFFSET -> AttributeRemover
Note: Clean up attributes
AttributeRemover
    REMOVE_ATTRS = _coordcount,_remnant,_coord,vertex_x,vertex_y,vertex_z
    -> GeometryCoercer
Note: Coerce to brep solid
GeometryCoercer
    KIND = fme_brep_solid
    COERCED -> Tester_4

Bookmark: Create end clipping tubes
Note: Extend line by radius
Extender
    LEN = $(DIAMETER)
    BEGINNING -> AttributeCreator_3
    END -> AttributeCreator_4
Note: Set begin/end flags
AttributeCreator_3
    ATTR_LIST = _extend,begin
    -> Chopper
AttributeCreator_4
    ATTR_LIST = _extend,end
    -> Chopper

Bookmark: Segment tubes
Note: Chop into segments
Chopper
    MAX_VERTICES = 2
    MODE = By Vertex
    REMNANT_ATTR = _remnant
    CHOPPED -> PythonCaller
    UNTOUCHED -> PythonCaller
Note: Calculate segment / quaternions
PythonCaller
    NEW_ATTRIBUTES = _vector_x _vector_y _vector_z _rotation _length
    PYTHONSOURCE:
      import fmeobjects
      import math
      # Template Function interface:
      def calcQuaternion(feature):
         start = feature.getCoordinate(0)
         end = feature.getCoordinate(1)
         vector = [(end[0]-start[0]),(end[1]-start[1]),(end[2]-start[2])]
         length = math.sqrt((end[0]-start[0])**2 + (end[1]-start[1])**2 + (end[2]-start[2])**2)
         vertical = [0,0,length]
         cross =  [vertical[1]*vector[2] - vertical[2]*vector[1],vertical[2]*vector[0] - vertical[0]*vector[2],vertical[0]*vector[1] - vertical[1]*vector[0]]
         dot = vertical[0]*vector[0] + vertical[1]*vector[1] + vertical[2]*vector[2]
         cos = dot/(length**2)
         # in some edge cases, a slightly out of bounds cos may be created
         if cos > 1.0:
             cos = 1.0
         if cos < -1.0:
             cos = -1.0
         rotation = math.acos(cos)*180/math.pi
         feature.setAttribute('_vector_x',cross[0])
         feature.setAttribute('_vector_y',cross[1])
         feature.setAttribute('_vector_z',cross[2])
         feature.setAttribute('_rotation',rotation)
         if rotation == 180 and cross == [0,0,0]:
             feature.setAttribute('_length',-length)
         else:
             feature.setAttribute('_length',length)
    PYTHONSYMBOL = calcQuaternion
    -> CoordinateExtractor
Note: Extract first / point coordinate
CoordinateExtractor
    IND = 0
    X_ATTR = _x
    Y_ATTR = _y
    Z_ATTR = _z
    Z_DEFAULT = -9999
    -> AttributeCreator
Note: Create XML for circle
AttributeCreator
    ATTR_LIST = _geometry,<geometry><ellipse><arc><centerCoord x="0" y="0" z="0"/><primRadius>$(DIAMETER)</primRadius><secRadius>$(DIAMETER)</secRadius><rotation>0</rotation><startAngle>0</startAngle><sweepAngle>-360</sweepAngle></arc></ellipse></geometry>
    -> MeasureExtractor_3
Note: Extract forward measure
MeasureExtractor_3
    GEOM_TYPE = Individual Vertex by Index
    INDEX = 0
    MEASURE_ATTR = _forward
    MEASURE_NAME = forward
    -> MeasureExtractor_4
Note: Extract reverse measure
MeasureExtractor_4
    GEOM_TYPE = Individual Vertex by Index
    INDEX = -1
    MEASURE_ATTR = _reverse
    MEASURE_NAME = reverse
    -> GeometryReplacer
Note: Create geometry from XML
GeometryReplacer
    ATTR = _geometry
    KIND_LONG = FME XML
    -> Extruder
Note: Extrude circle by / segment length
Extruder
    EXTRUSION_HEIGHT = @Value(_length)
    EXTRUSION_VECTOR_INPUT = Height
    -> Tester_2
Note: Test for vertical segment
Tester_2
    BOOL_OP = AND
    TEST_CLAUSE:
      TEST @Value(_vector_x) = 0
      TEST @Value(_vector_y) = 0
      TEST @Value(_vector_z) = 0
    TEST_MODE = Automatic
    PASSED -> Offsetter
    FAILED -> 3DRotator
Note: Rotate non-vertical / segments into alignment
3DRotator
    ANGLE = @Value(_rotation)
    AXIS_CHOICE = Custom Axis
    XDIR = @Value(_vector_x)
    XORIG = 0
    YDIR = @Value(_vector_y)
    YORIG = 0
    ZDIR = @Value(_vector_z)
    ZORIG = 0
    ROTATED -> Offsetter
Note: Offset tube into location
Offsetter
    XOFF = @Value(_x)
    YOFF = @Value(_y)
    ZOFF = @Value(_z)
    OFFSET -> AttributeRemover_2
Note: Clean up attributes
AttributeRemover_2
    REMOVE_ATTRS = _remnant,_vector_x,_vector_y,_vector_z,_rotation,_length,_x,_y,_z,_geometry
    -> GeometryCoercer_2
Note: Coerce to brep solid
GeometryCoercer_2
    KIND = fme_brep_solid
    COERCED -> TestFilter
Note: Filter out end clippers
TestFilter
    DEFAULT_VALUE = <UNFILTERED>
    TEST_LIST = BOOL_OP,OR,COMPOSITE_TEST,<Unused>,TEST_CLAUSE,"TEST @Value(_extend) = begin",BEGIN,BOOL_OP,OR,COMPOSITE_TEST,<Unused>,TEST_CLAUSE,"TEST @Value(_extend) = end",END
    BEGIN -> Clipper_2 [CLIPPER]
    END -> Clipper_3 [CLIPPER]
    <UNFILTERED> -> Tester_4

Bookmark: Clip vertex spheres near beginning and end
Note: Extract vertex spheres / within one radius of beginning
Tester_4
    BOOL_OP = OR
    TEST_CLAUSE:
      TEST @Value(_forward) >= $(DIAMETER)
      TEST @Value(_forward) = 0
      TEST @Value(_poly) = 1
    TEST_MODE = Automatic
    PASSED -> Tester_5
    FAILED -> Clipper_2 [CLIPPEE]
Note: Clip by begin tube
Clipper_2
    BOUNDARY_CASES = Treat as Inside
    CLIPPED_ATTR = _clipped
    CLIP_TYPE = Multiple Clippers
    CREATE_AGGREGATES = Yes
    GROUP_BY = _seg_id
    MERGE_ATTRS = No
    PRESERVE_CLIPPEE_EXTENTS = No
    OUTSIDE -> Tester_5
    <REJECTED> -> Clipper_2__REJECTED_
Note: Extract vertex spheres / within one radius of end
Tester_5
    BOOL_OP = OR
    TEST_CLAUSE:
      TEST @Value(_reverse) >= $(DIAMETER)
      TEST @Value(_reverse) = 0
      TEST @Value(_poly) = 1
    TEST_MODE = Automatic
    PASSED -> Aggregator
    FAILED -> Clipper_3 [CLIPPEE]
Note: Clip by end tube
Clipper_3
    BOUNDARY_CASES = Treat as Inside
    CLIPPED_ATTR = _clipped
    CLIP_TYPE = Multiple Clippers
    CREATE_AGGREGATES = Yes
    GROUP_BY = _seg_id
    MERGE_ATTRS = No
    PRESERVE_CLIPPEE_EXTENTS = No
    OUTSIDE -> Aggregator
    <REJECTED> -> Clipper_3__REJECTED_
Clipper_2__REJECTED_: Junction

Bookmark: Create bounding cube
Note: Get aggregate bounds
BoundsExtractor
    XMAX = _xmax
    XMIN = _xmin
    YMAX = _ymax
    YMIN = _ymin
    ZMAX = _zmax
    ZMIN = _zmin
    -> 2DBoxReplacer
Note: Replace with 2D / bounding box
2DBoxReplacer
    MAXXVALATTR = @Value(_xmax)
    MAXYVALATTR = @Value(_ymax)
    MINXVALATTR = @Value(_xmin)
    MINYVALATTR = @Value(_ymin)
    BOX -> 3DForcer
Note: Move bounding / box to lower Z
3DForcer
    KEEPZVAL = No
    ZVALATTR = @Value(_zmin)
    -> Extruder_2
Note: Extrude to upper Z
Extruder_2
    EXTRUSION_HEIGHT = @Value(_zmax)-@Value(_zmin)
    EXTRUSION_VECTOR_INPUT = Height
    -> AttributeRemover_4
Note: Clean up attributes
AttributeRemover_4
    REMOVE_ATTRS = _xmax,_xmin,_ymax,_ymin,_zmax,_zmin
    -> Clipper [CLIPPEE]

Bookmark: Solid Processing
Note: Clip bounding box / by multi-solid to get / true solid buffer
Clipper
    BOUNDARY_CASES = Treat as Inside
    CLIPPED_ATTR = _clipped
    CLIP_TYPE = Multiple Clippers
    CREATE_AGGREGATES = Yes
    GROUP_BY = _line_id fme_feature_type
    MERGE_ATTRS = No
    PRESERVE_CLIPPEE_EXTENTS = No
    INSIDE -> AttributeRemover_5
    <REJECTED> -> Clipper__REJECTED_
Note: Clean up attributes
AttributeRemover_5
    REMOVE_ATTRS = _forward,_reverse,_extend,_clipped,_fme_no_clipper
    -> AttributeRemover_11
Clipper__REJECTED_: Junction
