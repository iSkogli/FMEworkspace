FME workspace GML_NVDB2SOSIledning_Kontroll.fmw

Parameters:
- SourceDataset_LAS = C:\Users\ingsko\OneDrive - Statens Vegvesen\_IArbeid\Prosjekter\NVDBAPI2GML\SOSIledning_GML_data\eksport_408005_795_1.laz   # Source ASPRS LAS File(s)
- Source_GML_LandSurface = C:\DATA\TestdataGML\Vegprosjekter\Fv251Hellefossen\3_Fagmodeller_grunnlag\L0_Grunnlag\Veg\LandXML\12000 1_Overflate.gml   # Source Geography Markup Language (GML) File(s)
- Source_GML_NVDB_Trekkekum = C:\Users\ingsko\OneDrive - Statens Vegvesen\_IArbeid\Prosjekter\NVDBAPI2GML\NVDB_GML_data\LedningsregistreringHellefossen\Trekkekum.gml   # Source Geography Markup Language (GML) File(s)
- Source_GML_NVDB_Kum = C:\Users\ingsko\OneDrive - Statens Vegvesen\_IArbeid\Prosjekter\NVDBAPI2GML\NVDB_GML_data\LedningsregistreringHellefossen\Kum.gml   # Source Geography Markup Language (GML) File(s)
- Source_GML_FKB = C:\DATA\TestdataGML\Vegprosjekter\Fv251Hellefossen\3_Fagmodeller_grunnlag\L3_FKB_referanse\GML\FKB_Veg.gml   # Source Geography Markup Language (GML) File(s)
- Source_GML_LednReg_Kum = C:\Users\ingsko\OneDrive - Statens Vegvesen\_IArbeid\Prosjekter\NVDBAPI2GML\SOSIledning_GML_data\Hellefossen_LednReg_Kum.gml   # Source Geography Markup Language (GML) File(s)
- SourceDataset_GML = C:\Users\ingsko\OneDrive - Statens Vegvesen\_IArbeid\Prosjekter\NVDBAPI2GML\SOSIledning_GML_data\Hellefossen_NorskVann.gml   # Source Geography Markup Language (GML) File(s)

Readers:
- LAS_1: LAS from $(SourceDataset_LAS)
- GML_1: GML from $(Source_GML_LandSurface)
- GML_2: GML from $(Source_GML_FKB)
- GML_3: GML from $(Source_GML_LednReg_Kum)
- GML_4: GML from $(Source_GML_NVDB_Kum)
- GML_5: GML from $(Source_GML_NVDB_Trekkekum)
- GML_6: GML from $(SourceDataset_GML)

Note: Kontroll av data NVDB - SOSI Ledning

Bookmark: Feature input - NVDB
Kum (reader GML_4)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, sideposisjon xml_buffer, vegsystemreferanse.Vegsystemreferanse.vegsystem.DT_Vegsystem.vegkategori xml_buffer, vegsystemreferanse.Vegsystemreferanse.vegsystem.DT_Vegsystem.vegfase xml_buffer, vegsystemreferanse.Vegsystemreferanse.vegsystem.DT_Vegsystem.vegnummer xml_int64, vegsystemreferanse.Vegsystemreferanse.vegstrekning.DT_Vegsystem.vegkategori xml_buffer, vegsystemreferanse.Vegsystemreferanse.vegstrekning.DT_Vegsystem.vegfase xml_buffer, vegsystemreferanse.Vegsystemreferanse.vegstrekning.DT_Vegsystem.vegnummer xml_int64, vegsystemreferanse.Vegsystemreferanse.sideanlegg.DT_Sideanlegg.sideanleggsdel xml_int64, vegsystemreferanse.Vegsystemreferanse.sideanlegg.DT_Sideanlegg.fraMeter xml_int64, vegsystemreferanse.Vegsystemreferanse.sideanlegg.DT_Sideanlegg.tilMeter xml_int64, vegsystemreferanse.Vegsystemreferanse.kryssystem.DT_Kryssystem.kryssdel xml_int64, vegsystemreferanse.Vegsystemreferanse.kryssystem.DT_Kryssystem.fraMeter xml_int64, vegsystemreferanse.Vegsystemreferanse.kryssystem.DT_Kryssystem.tilMeter xml_int64, vegsystemreferanse.Vegsystemreferanse.vegsystemreferanseFraDato xml_date, vegsystemreferanse.Vegsystemreferanse.vegsystemreferanseTilDato xml_date,
      vegsystemreferanse.Vegsystemreferanse.referanseretning xml_buffer, type xml_buffer, bruksområde xml_buffer, materialtype xml_buffer, plassering xml_buffer, lokkRist_Type xml_buffer, spesiellBelegningRundtKum xml_buffer, diameter xml_real64, diameter_Åpning xml_real64, dybde xml_real64, dybdeTilUtløp xml_real64, bredde1_Firkantkum xml_real64, bredde2_Firkantkum xml_real64, avstandFraVegkant xml_real64, stige xml_buffer, harFlyteramme xml_buffer, avløp xml_buffer, dykker xml_buffer, oljeutskilling xml_buffer, antallRørInn xml_int64, antallHjelpesluker xml_int64, kumskjerm xml_buffer, oppslammingstid xml_buffer, inngårIDrenssystem xml_buffer, etableringsår xml_int64, driftsmerking xml_buffer, produsent xml_buffer, produktnavn xml_buffer, leverandør xml_buffer, tilleggsinformasjon xml_buffer,
      arkivreferanse xml_buffer, prosjektreferanse xml_buffer, FKB_ID xml_buffer, eier xml_buffer, eier_Navn xml_buffer, vedlikeholdsansvarlig xml_buffer, posisjon xml_geometry, lineærPosisjon{}.LineærPosisjonPunkt.lineærReferanseMetode xml_buffer, lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer, lineærPosisjon{}.LineærPosisjonPunkt.nettverkselement.xlink_role xml_buffer, lineærPosisjon{}.LineærPosisjonPunkt.nettverkselement.xlink_title xml_buffer, lineærPosisjon{}.LineærPosisjonPunkt.nettverkselement.owns xml_boolean, lineærPosisjon{}.LineærPosisjonPunkt.posisjon xml_real64, assosiertKommentar{}.owns xml_boolean, assosiertKommentar{}.nilReason xml_buffer, assosiertKommentar{}.gml_remoteSchema xml_buffer, assosiertKommentar{}.xlink_href xml_buffer, assosiertKommentar{}.xlink_role xml_buffer, assosiertKommentar{}.xlink_title xml_buffer, assosiertLukketRørgrøft.owns xml_boolean, assosiertLukketRørgrøft.nilReason xml_buffer, assosiertLukketRørgrøft.gml_remoteSchema xml_buffer, assosiertLukketRørgrøft.xlink_href xml_buffer, assosiertLukketRørgrøft.xlink_role xml_buffer, assosiertLukketRørgrøft.xlink_title xml_buffer, assosiertStikkrenneKulvert.owns xml_boolean,
      assosiertStikkrenneKulvert.nilReason xml_buffer, assosiertStikkrenneKulvert.gml_remoteSchema xml_buffer, assosiertStikkrenneKulvert.xlink_href xml_buffer, assosiertStikkrenneKulvert.xlink_role xml_buffer, assosiertStikkrenneKulvert.xlink_title xml_buffer, assosiertSystemobjekt{}.owns xml_boolean, assosiertSystemobjekt{}.nilReason xml_buffer, assosiertSystemobjekt{}.gml_remoteSchema xml_buffer, assosiertSystemobjekt{}.xlink_href xml_buffer, assosiertSystemobjekt{}.xlink_role xml_buffer, assosiertSystemobjekt{}.xlink_title xml_buffer, assosiertTilstandsgrad_Kum{}.owns xml_boolean, assosiertTilstandsgrad_Kum{}.nilReason xml_buffer, assosiertTilstandsgrad_Kum{}.gml_remoteSchema xml_buffer, assosiertTilstandsgrad_Kum{}.xlink_href xml_buffer, assosiertTilstandsgrad_Kum{}.xlink_role xml_buffer, assosiertTilstandsgrad_Kum{}.xlink_title xml_buffer, assosiertTilstandSkade_Punkt{}.owns xml_boolean, assosiertTilstandSkade_Punkt{}.nilReason xml_buffer, assosiertTilstandSkade_Punkt{}.gml_remoteSchema xml_buffer, assosiertTilstandSkade_Punkt{}.xlink_href xml_buffer, assosiertTilstandSkade_Punkt{}.xlink_role xml_buffer, assosiertTilstandSkade_Punkt{}.xlink_title xml_buffer, assosiertTilstandSkadeFU_Punkt{}.owns xml_boolean, assosiertTilstandSkadeFU_Punkt{}.nilReason xml_buffer, assosiertTilstandSkadeFU_Punkt{}.gml_remoteSchema xml_buffer, assosiertTilstandSkadeFU_Punkt{}.xlink_href xml_buffer, assosiertTilstandSkadeFU_Punkt{}.xlink_role xml_buffer, assosiertTilstandSkadeFU_Punkt{}.xlink_title xml_buffer, assosiertTunnelløp.owns xml_boolean,
      assosiertTunnelløp.nilReason xml_buffer, assosiertTunnelløp.gml_remoteSchema xml_buffer, assosiertTunnelløp.xlink_href xml_buffer, assosiertTunnelløp.xlink_role xml_buffer, assosiertTunnelløp.xlink_title xml_buffer, assosiertVannhåndteringsanlegg.owns xml_boolean, assosiertVannhåndteringsanlegg.nilReason xml_buffer, assosiertVannhåndteringsanlegg.gml_remoteSchema xml_buffer, assosiertVannhåndteringsanlegg.xlink_href xml_buffer, assosiertVannhåndteringsanlegg.xlink_role xml_buffer, assosiertVannhåndteringsanlegg.xlink_title xml_buffer, assosiertDokumentasjon{}.owns xml_boolean, assosiertDokumentasjon{}.nilReason xml_buffer, assosiertDokumentasjon{}.gml_remoteSchema xml_buffer, assosiertDokumentasjon{}.xlink_href xml_buffer, assosiertDokumentasjon{}.xlink_role xml_buffer, assosiertDokumentasjon{}.xlink_title xml_buffer
    -> Reprojector
Reprojector
    DEST = EPSG:25832
    INTERPOLATION_TYPE_NAME = Nearest Neighbor
    RASTER_CELL_SIZE = Preserve Cells
    RASTER_TOLERANCE = 0.0
    SOURCE = Read from feature
    REPROJECTED -> GML-NVDB-Kum
GML-NVDB-Kum: Inspector
Trekkekum (reader GML_5)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, sideposisjon xml_buffer, vegsystemreferanse.Vegsystemreferanse.vegsystem.DT_Vegsystem.vegkategori xml_buffer, vegsystemreferanse.Vegsystemreferanse.vegsystem.DT_Vegsystem.vegfase xml_buffer, vegsystemreferanse.Vegsystemreferanse.vegsystem.DT_Vegsystem.vegnummer xml_int64, vegsystemreferanse.Vegsystemreferanse.vegstrekning.DT_Vegsystem.vegkategori xml_buffer, vegsystemreferanse.Vegsystemreferanse.vegstrekning.DT_Vegsystem.vegfase xml_buffer, vegsystemreferanse.Vegsystemreferanse.vegstrekning.DT_Vegsystem.vegnummer xml_int64, vegsystemreferanse.Vegsystemreferanse.sideanlegg.DT_Sideanlegg.sideanleggsdel xml_int64, vegsystemreferanse.Vegsystemreferanse.sideanlegg.DT_Sideanlegg.fraMeter xml_int64, vegsystemreferanse.Vegsystemreferanse.sideanlegg.DT_Sideanlegg.tilMeter xml_int64, vegsystemreferanse.Vegsystemreferanse.kryssystem.DT_Kryssystem.kryssdel xml_int64, vegsystemreferanse.Vegsystemreferanse.kryssystem.DT_Kryssystem.fraMeter xml_int64, vegsystemreferanse.Vegsystemreferanse.kryssystem.DT_Kryssystem.tilMeter xml_int64, vegsystemreferanse.Vegsystemreferanse.vegsystemreferanseFraDato xml_date, vegsystemreferanse.Vegsystemreferanse.vegsystemreferanseTilDato xml_date,
      vegsystemreferanse.Vegsystemreferanse.referanseretning xml_buffer, kumform xml_buffer, plassering xml_buffer, materiale_Kum xml_buffer, materiale_Lokk xml_buffer, brannsikker xml_buffer, diameter_Ytre xml_real64, bredde_Ytre xml_real64, lengde_Ytre xml_real64, dybde_Ytre xml_real64, antallRør xml_int64, tilleggsinformasjon xml_buffer, etableringsår xml_int64, driftsmerking xml_buffer, produsent xml_buffer, produktnavn xml_buffer, arkivnummer xml_buffer, arkivreferanse xml_buffer, prosjektreferanse xml_buffer, FKB_ID xml_buffer, eier xml_buffer, eier_Navn xml_buffer, vedlikeholdsansvarlig xml_buffer, posisjon xml_geometry, lineærPosisjon{}.LineærPosisjonPunkt.lineærReferanseMetode xml_buffer, lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer,
      lineærPosisjon{}.LineærPosisjonPunkt.nettverkselement.xlink_role xml_buffer, lineærPosisjon{}.LineærPosisjonPunkt.nettverkselement.xlink_title xml_buffer, lineærPosisjon{}.LineærPosisjonPunkt.nettverkselement.owns xml_boolean, lineærPosisjon{}.LineærPosisjonPunkt.posisjon xml_real64, assosiertKommentar{}.owns xml_boolean, assosiertKommentar{}.nilReason xml_buffer, assosiertKommentar{}.gml_remoteSchema xml_buffer, assosiertKommentar{}.xlink_href xml_buffer, assosiertKommentar{}.xlink_role xml_buffer, assosiertKommentar{}.xlink_title xml_buffer, assosiertTilstandSkade_Punkt{}.owns xml_boolean, assosiertTilstandSkade_Punkt{}.nilReason xml_buffer, assosiertTilstandSkade_Punkt{}.gml_remoteSchema xml_buffer, assosiertTilstandSkade_Punkt{}.xlink_href xml_buffer, assosiertTilstandSkade_Punkt{}.xlink_role xml_buffer, assosiertTilstandSkade_Punkt{}.xlink_title xml_buffer, assosiertTilstandSkadeFU_Punkt{}.owns xml_boolean, assosiertTilstandSkadeFU_Punkt{}.nilReason xml_buffer, assosiertTilstandSkadeFU_Punkt{}.gml_remoteSchema xml_buffer, assosiertTilstandSkadeFU_Punkt{}.xlink_href xml_buffer, assosiertTilstandSkadeFU_Punkt{}.xlink_role xml_buffer, assosiertTilstandSkadeFU_Punkt{}.xlink_title xml_buffer, assosiertTunnelløp.owns xml_boolean, assosiertTunnelløp.nilReason xml_buffer, assosiertTunnelløp.gml_remoteSchema xml_buffer, assosiertTunnelløp.xlink_href xml_buffer, assosiertTunnelløp.xlink_role xml_buffer, assosiertTunnelløp.xlink_title xml_buffer, assosiertTunnelløpUtenTrafikk.owns xml_boolean, assosiertTunnelløpUtenTrafikk.nilReason xml_buffer,
      assosiertTunnelløpUtenTrafikk.gml_remoteSchema xml_buffer, assosiertTunnelløpUtenTrafikk.xlink_href xml_buffer, assosiertTunnelløpUtenTrafikk.xlink_role xml_buffer, assosiertTunnelløpUtenTrafikk.xlink_title xml_buffer, assosiertDokumentasjon{}.owns xml_boolean, assosiertDokumentasjon{}.nilReason xml_buffer, assosiertDokumentasjon{}.gml_remoteSchema xml_buffer, assosiertDokumentasjon{}.xlink_href xml_buffer, assosiertDokumentasjon{}.xlink_role xml_buffer, assosiertDokumentasjon{}.xlink_title xml_buffer
    -> Reprojector_2
Reprojector_2
    DEST = EPSG:25832
    INTERPOLATION_TYPE_NAME = Nearest Neighbor
    RASTER_CELL_SIZE = Preserve Cells
    RASTER_TOLERANCE = 0.0
    SOURCE = Read from feature
    REPROJECTED -> GML-NVDB-Trekkekum
GML-NVDB-Trekkekum: Inspector

Bookmark: Feature output - Ledningsregistreringsforskriften
Kum (reader GML_3)
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, hovedbruk xml_buffer, ytreDiameter xml_real64, posisjon xml_geometry, omriss xml_geometry, ytreHøyde xml_real64
    -> Reprojector_3
Reprojector_3
    DEST = EPSG:25832
    INTERPOLATION_TYPE_NAME = Nearest Neighbor
    RASTER_CELL_SIZE = Preserve Cells
    RASTER_TOLERANCE = 0.0
    SOURCE = Read from feature
    REPROJECTED -> GML-Ledningsreg-Kum
GML-Ledningsreg-Kum: Inspector

Bookmark: Feature output - Norsk vann - prosjektering
VA_Kum (reader GML_6)
    attributes: datasett_navn xml_buffer, datasett_versjonsnr xml_int64, datauttaksdato xml_date, endringsflagg.Endringsflagg.endretEgenskap xml_buffer, endringsflagg.Endringsflagg.endretGeometri xml_buffer, endringsflagg.Endringsflagg.endring_referanse xml_buffer, endringsflagg.Endringsflagg.endringÅrsak xml_buffer, endringsflagg.Endringsflagg.endringBeskrivelse xml_buffer, endringsflagg.Endringsflagg.tidspunktEndring xml_datetime, endringsflagg.Endringsflagg.typeEndring xml_buffer, identifikasjon.Identifikasjon.guid xml_buffer, identifikasjon.Identifikasjon.lokalId xml_buffer, identifikasjon.Identifikasjon.navnerom xml_buffer, informasjon xml_buffer, kommune xml_buffer, kvalitet.Posisjonskvalitet.målemetode xml_buffer, kvalitet.Posisjonskvalitet.målemetodeHøyde xml_buffer, kvalitet.Posisjonskvalitet.nøyaktighet xml_int64, kvalitet.Posisjonskvalitet.nøyaktighetHøyde xml_int64, leveransetype xml_buffer, link_referanse{} xml_buffer, prosjektnavn xml_buffer, stedfestingsforhold xml_buffer, anleggsår xml_int64, bredde xml_real64, driftsattår.Komponentdatering.årstall xml_int64, driftsmerking xml_buffer, eier.Eier.eier xml_buffer, eier.Eier.eiertype xml_buffer, form xml_geometry,
      høyde xml_real64, høydereferanse xml_buffer, konstruksjon xml_buffer, konstruksjonsmateriale xml_buffer, kumbruk.VA_Kumbruk.felles xml_boolean, kumbruk.VA_Kumbruk.overvann xml_boolean, kumbruk.VA_Kumbruk.spillvann xml_boolean, kumbruk.VA_Kumbruk.vann xml_boolean, kumform xml_buffer, kumtype xml_buffer, lengde xml_real64, omriss xml_geometry, posisjon xml_geometry, status xml_buffer, stige xml_buffer, volum xml_real64
    -> Reprojector_4
Reprojector_4
    DEST = EPSG:25832
    INTERPOLATION_TYPE_NAME = Nearest Neighbor
    RASTER_CELL_SIZE = Preserve Cells
    RASTER_TOLERANCE = 0.0
    SOURCE = Read from feature
    REPROJECTED -> GML-NorskVann-VA_Kum
GML-NorskVann-VA_Kum: Inspector

Bookmark: Høydedata
LAS (reader LAS_1)
    -> PointCloudSplitter
PointCloudSplitter
    OUTPUT_ATTR = _classification
    SPLIT_BY_DISPLAY = classification
    SPLIT_TYPE = Unique
    SPLIT -> PointCloudLASClassifier [LAS_Point_Cloud]
PointCloudLASClassifier
    1-Unclassified -> LAS_1-Unclassified
    2-Ground -> LAS_2-Ground
    3-Low_Vegetation -> LAS_3-Low_Vegetation
    4-Medium_Vegetation -> LAS_4-Medium_Vegetation
    5-High_Vegetation -> LAS_5-High_Vegetation
    6-Building -> LAS_6-Building
    7-Low_Point_/Noise/ -> LAS_7-Low_Point__Noise_
    8-Model_Key_Point_/Mass_Point/ -> LAS_8-Model_Key_Point__Mass_Point_
    9-Water -> LAS_9-Water
LAS_1-Unclassified: Inspector
LAS_2-Ground: Inspector
LAS_3-Low_Vegetation: Inspector
LAS_4-Medium_Vegetation: Inspector
LAS_5-High_Vegetation: Inspector
LAS_6-Building: Inspector
LAS_7-Low_Point__Noise_: Inspector
LAS_8-Model_Key_Point__Mass_Point_: Inspector
LAS_9-Water: Inspector
LandSurface (reader GML_1)
    attributes: spatialRepresentation{}.SpatialRepresentation.name xml_buffer, spatialRepresentation{}.SpatialRepresentation.description xml_buffer, spatialRepresentation{}.SpatialRepresentation.geometry xml_geometry, spatialRepresentation{}.SpatialRepresentation.crs xml_xml, spatialRepresentation{}.SpatialRepresentation.crs.nilReason xml_buffer, spatialRepresentation{}.SpatialRepresentation.crs.gml_remoteSchema xml_buffer, spatialRepresentation{}.SpatialRepresentation.crs.xlink_href xml_buffer, spatialRepresentation{}.SpatialRepresentation.crs.xlink_role xml_buffer, spatialRepresentation{}.SpatialRepresentation.crs.xlink_title xml_buffer, linearlyReferencedLocation{} xml_xml, propertySet{}.nilReason xml_buffer, propertySet{}.gml_remoteSchema xml_buffer, propertySet{}.xlink_href xml_buffer, propertySet{}.xlink_role xml_buffer, propertySet{}.xlink_title xml_buffer, propertySet{}.owns xml_boolean, propertySet{}.PropertySet.gml_id xml_buffer, propertySet{}.PropertySet.propertySet{} xml_xml, propertySet{}.PropertySet.propertySet{}.nilReason xml_buffer, propertySet{}.PropertySet.propertySet{}.gml_remoteSchema xml_buffer, propertySet{}.PropertySet.propertySet{}.xlink_href xml_buffer, propertySet{}.PropertySet.propertySet{}.xlink_role xml_buffer, propertySet{}.PropertySet.propertySet{}.xlink_title xml_buffer, propertySet{}.PropertySet.propertySet{}.owns xml_boolean, propertySet{}.PropertySet.property{}.nilReason xml_buffer, propertySet{}.PropertySet.property{}.gml_remoteSchema xml_buffer, propertySet{}.PropertySet.property{}.xlink_href xml_buffer, propertySet{}.PropertySet.property{}.xlink_role xml_buffer, propertySet{}.PropertySet.property{}.xlink_title xml_buffer, propertySet{}.PropertySet.property{}.owns xml_boolean,
      propertySet{}.PropertySet.property{}.Property.gml_id xml_buffer, propertySet{}.PropertySet.property{}.Property.valueType xml_buffer, propertySet{}.PropertySet.property{}.Property.value{} xml_xml, propertySet{}.PropertySet.property{}.Property.units xml_buffer, propertySet{}.PropertySet.property{}.Property.cardinality xml_buffer, propertySet{}.PropertySet.authority xml_buffer, propertySet{}.PropertySet.propertyMember{}.nilReason xml_buffer, propertySet{}.PropertySet.propertyMember{}.gml_remoteSchema xml_buffer, propertySet{}.PropertySet.propertyMember{}.xlink_href xml_buffer, propertySet{}.PropertySet.propertyMember{}.xlink_role xml_buffer, propertySet{}.PropertySet.propertyMember{}.xlink_title xml_buffer, propertySet{}.PropertySet.propertyMember{}.owns xml_boolean, propertySet{}.PropertySet.propertyMember{}.Property.gml_id xml_buffer, propertySet{}.PropertySet.propertyMember{}.Property.valueType xml_buffer, propertySet{}.PropertySet.propertyMember{}.Property.value{} xml_xml, propertySet{}.PropertySet.propertyMember{}.Property.units xml_buffer, propertySet{}.PropertySet.propertyMember{}.Property.cardinality xml_buffer, property{}.nilReason xml_buffer, property{}.gml_remoteSchema xml_buffer, property{}.xlink_href xml_buffer, property{}.xlink_role xml_buffer, property{}.xlink_title xml_buffer, property{}.owns xml_boolean, property{}.Property.gml_id xml_buffer, property{}.Property.valueType xml_buffer, property{}.Property.value{} xml_xml, property{}.Property.units xml_buffer, property{}.Property.cardinality xml_buffer, landFeatureID.ID.identifier xml_buffer, landFeatureID.ID.scope xml_buffer,
      state xml_buffer, landSurfaceID.ID.identifier xml_buffer, landSurfaceID.ID.scope xml_buffer, spatialRepresentation xml_geometry, material xml_buffer
    -> GML-LandInfra-LandSurface-Vegmodell_overflate
GML-LandInfra-LandSurface-Vegmodell_overflate: Inspector

Bookmark: FKB
Vegdekkekant (reader GML_2)
    attributes: identifikasjon.Identifikasjon.lokalId xml_buffer, identifikasjon.Identifikasjon.navnerom xml_buffer, identifikasjon.Identifikasjon.versjonId xml_buffer, datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry, nedsenketKantstein xml_boolean, høydereferanse xml_buffer, medium xml_buffer
    -> GML-FKB-Vegdekkekant
GML-FKB-Vegdekkekant: Inspector
VeggrøftÅpen (reader GML_2)
    attributes: identifikasjon.Identifikasjon.lokalId xml_buffer, identifikasjon.Identifikasjon.navnerom xml_buffer, identifikasjon.Identifikasjon.versjonId xml_buffer, datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry
    -> GML-FKB-VeggrøftÅpen
GML-FKB-VeggrøftÅpen: Inspector

FME custom transformer PointCloudLASClassifier
The transformer uses _classification attribute for outputting each class through its own port. It also sets _classification_description attribute, which contains the explanation of the class assigned to a point cloud.
The transformer does not split the cloud, it only helps separate point clouds after splitting and easily identify the content of each class.
The classification values are assigned based on the standard ASPRS classification values:
0 - Created, never classified
1 - Unclassified
2 - Ground
3 - Low Vegetation
4 - Medium Vegetation
5 - High Vegetation
6 - Building
7 - Low Point (Noise)
8 - Model Key point (Mass Point)
9 - Water
10 - Reserved for ASPRS Definition
11 - Reserved fro ASPRS Definition
12 - Overlap Points
13-31 - Reserved for ASPRS Definition

Note: PointCloudLASClassifier is a custom transformer which routes point clouds into different output port depending on their classification attribute, which is assigned to point clouds / in PointCloudSplitter - this transformer should be placed before PointCloudLASClassifier. / PointCloudLASClassifier also adds a classification_description / attribute to each point cloud.
LAS_Point_Cloud (input)
    -> AttributeExposer
Note: Expose _classification attribute
AttributeExposer
    ATTR_LIST = _classification
    -> AttributeValueMapper
Note: Map the contents of the _classification attribute / to _classification_description attribute
AttributeValueMapper
    DEFAULT_VALUE = Reserved for ASPRS Definition
    DIRECTION = Forward (Source To Destination)
    LUT = 0,Created, never classified,1,Unclassified,2,Ground,3,Low Vegetation,4,Medium Vegetation,5,High Vegetation,6,Building,7,Low Point (noise),8,Model Key-point (mass point),9,Water,10,Reserved for ASPRS Definition,11,Reserved for ASPRS Definition,12,Overlap Points,13,Reserved for ASPRS Definition
    SRC = _classification
    VAL_ATTR = _classification_description
    -> PC
Note: Route point clouds into appriopriate ports / based on _classification attribute
PC: TestFilter
    DEFAULT_VALUE = <UNFILTERED>
    TEST_LIST = TEST_CLAUSE,"TEST @Value(_classification) = 0",TEST_LIST,"&_classification,=,0",TEST_MODE,Automatic,BOOL_OP,OR,0-Created(NeverClassified),TEST_CLAUSE,"TEST @Value(_classification) = 1",TEST_LIST,"&_classification,=,1",TEST_MODE,Automatic,BOOL_OP,OR,1-Unclassified,TEST_CLAUSE,"TEST @Value(_classification) = 2",TEST_LIST,"&_classification,=,2",TEST_MODE,Automatic,BOOL_OP,OR,2-Ground,TEST_CLAUSE,"TEST @Value(_classification) = 3",TEST_LIST,"&_classification,=,3",TEST_MODE,Automatic,BOOL_OP,OR,3-LowVegetation,TEST_CLAUSE,"TEST @Value(_classification) = 4",TEST_LIST,"&_classification,=,4",TEST_MODE,Automatic,BOOL_OP,OR,4-MediumVegetation,TEST_CLAUSE,"TEST @Value(_classification) = 5",TEST_LIST,"&_classification,=,5",TEST_MODE,Automatic,BOOL_OP,OR,5-HighVegetation,TEST_CLAUSE,"TEST @Value(_classification) = 6",TEST_LIST,"&_classification,=,6",TEST_MODE,Automatic,BOOL_OP,OR,6-Building,TEST_CLAUSE,"TEST @Value(_classification) = 7",TEST_LIST,"&_classification,=,7",TEST_MODE,Automatic,BOOL_OP,OR,7-LowPoint(Noise),TEST_CLAUSE,"TEST @Value(_classification) = 8",TEST_LIST,"&_classification,=,8",TEST_MODE,Automatic,BOOL_OP,OR,8-ModelKeyPoint(MassPoint),TEST_CLAUSE,"TEST @Value(_classification) = 9",TEST_LIST,"&_classification,=,9",TEST_MODE,Automatic,BOOL_OP,OR,9-Water,TEST_CLAUSE,"TEST @Value(_classification) = 10",TEST_LIST,"&_classification,=,10",TEST_MODE,Automatic,BOOL_OP,OR,10-Reserved for ASPRS Definition,TEST_CLAUSE,"TEST @Value(_classification) = 11",TEST_LIST,"&_classification,=,11",TEST_MODE,Automatic,BOOL_OP,OR,11-Reserved for ASPRS Definition,TEST_CLAUSE,"TEST @Value(_classification) = 12",TEST_LIST,"&_classification,=,12",TEST_MODE,Automatic,BOOL_OP,OR,12-OverlapPoints,TEST_CLAUSE,"TEST @Value(_classification) >= 13",TEST_LIST,"&_classification,>=,13",TEST_MODE,Automatic,BOOL_OP,OR,13more-Reserved for ASPRS Definition
    0-Created(NeverClassified) -> 0-Created/NeverClassified/ (output)
    1-Unclassified -> 1-Unclassified (output)
    2-Ground -> 2-Ground (output)
    3-LowVegetation -> 3-Low_Vegetation (output)
    4-MediumVegetation -> 4-Medium_Vegetation (output)
    5-HighVegetation -> 5-High_Vegetation (output)
    6-Building -> 6-Building (output)
    7-LowPoint(Noise) -> 7-Low_Point_/Noise/ (output)
    8-ModelKeyPoint(MassPoint) -> 8-Model_Key_Point_/Mass_Point/ (output)
    9-Water -> 9-Water (output)
    10-Reserved for ASPRS Definition -> 10_Reserved_for_ASPRS_Definition (output)
    11-Reserved for ASPRS Definition -> 11-Reserved_for_ASPRS_Definition (output)
    12-OverlapPoints -> 12-Overlap_Points (output)
    13more-Reserved for ASPRS Definition -> 13more-Reserved_for_ASPRS_Definition (output)
0-Created/NeverClassified/ (output)
1-Unclassified (output)
2-Ground (output)
3-Low_Vegetation (output)
4-Medium_Vegetation (output)
5-High_Vegetation (output)
6-Building (output)
7-Low_Point_/Noise/ (output)
8-Model_Key_Point_/Mass_Point/ (output)
9-Water (output)
10_Reserved_for_ASPRS_Definition (output)
11-Reserved_for_ASPRS_Definition (output)
12-Overlap_Points (output)
13more-Reserved_for_ASPRS_Definition (output)
