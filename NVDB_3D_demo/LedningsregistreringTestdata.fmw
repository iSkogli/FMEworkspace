FME workspace LedningsregistreringTestdata.fmw

Parameters:
- SourceDataset_GML = C:\DATA\TestdataGML\SOSI Ledning\EksempelData_LedningsnettEtablertEllerFlyttet_v20190101.gml   # Source Geography Markup Language (GML) File(s)

Readers:
- GML_1: GML from $(SourceDataset_GML)

Bookmark: Framføringsveger
Trase (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, beliggenhet xml_geometry, stedfestingsårsak xml_buffer, stedfestingsforhold xml_buffer, tilKobling.nilReason xml_buffer, tilKobling.gml_remoteSchema xml_buffer,
      tilKobling.xlink_href xml_buffer, tilKobling.xlink_role xml_buffer, tilKobling.xlink_title xml_buffer, tilKobling.owns xml_boolean, fraKobling.nilReason xml_buffer, fraKobling.gml_remoteSchema xml_buffer, fraKobling.xlink_href xml_buffer, fraKobling.xlink_role xml_buffer, fraKobling.xlink_title xml_buffer, fraKobling.owns xml_boolean, stikkledning xml_buffer, bruk{} xml_buffer, indreBredde xml_real64, indreHøyde xml_real64, ytreBredde xml_real64, ytreHøyde xml_real64, indreDiameter xml_real64, ytreDiameter xml_real64
    -> Trase
Trase: Inspector
Kulvert (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, beliggenhet xml_geometry, stedfestingsårsak xml_buffer, stedfestingsforhold xml_buffer, tilKobling.nilReason xml_buffer, tilKobling.gml_remoteSchema xml_buffer,
      tilKobling.xlink_href xml_buffer, tilKobling.xlink_role xml_buffer, tilKobling.xlink_title xml_buffer, tilKobling.owns xml_boolean, fraKobling.nilReason xml_buffer, fraKobling.gml_remoteSchema xml_buffer, fraKobling.xlink_href xml_buffer, fraKobling.xlink_role xml_buffer, fraKobling.xlink_title xml_buffer, fraKobling.owns xml_boolean, stikkledning xml_buffer, bruk{} xml_buffer, indreBredde xml_real64, indreHøyde xml_real64, ytreBredde xml_real64, ytreHøyde xml_real64, indreDiameter xml_real64, ytreDiameter xml_real64
    -> Kulvert
Kulvert: Inspector
Kanal (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, beliggenhet xml_geometry, stedfestingsårsak xml_buffer, stedfestingsforhold xml_buffer, tilKobling.nilReason xml_buffer, tilKobling.gml_remoteSchema xml_buffer,
      tilKobling.xlink_href xml_buffer, tilKobling.xlink_role xml_buffer, tilKobling.xlink_title xml_buffer, tilKobling.owns xml_boolean, fraKobling.nilReason xml_buffer, fraKobling.gml_remoteSchema xml_buffer, fraKobling.xlink_href xml_buffer, fraKobling.xlink_role xml_buffer, fraKobling.xlink_title xml_buffer, fraKobling.owns xml_boolean, stikkledning xml_buffer, bruk{} xml_buffer, indreBredde xml_real64, indreHøyde xml_real64, ytreBredde xml_real64, ytreHøyde xml_real64, indreDiameter xml_real64, ytreDiameter xml_real64
    -> Kanal
Kanal: Inspector
Tunnel (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, beliggenhet xml_geometry, stedfestingsårsak xml_buffer, stedfestingsforhold xml_buffer, tilKobling.nilReason xml_buffer, tilKobling.gml_remoteSchema xml_buffer,
      tilKobling.xlink_href xml_buffer, tilKobling.xlink_role xml_buffer, tilKobling.xlink_title xml_buffer, tilKobling.owns xml_boolean, fraKobling.nilReason xml_buffer, fraKobling.gml_remoteSchema xml_buffer, fraKobling.xlink_href xml_buffer, fraKobling.xlink_role xml_buffer, fraKobling.xlink_title xml_buffer, fraKobling.owns xml_boolean, stikkledning xml_buffer, bruk{} xml_buffer, indreBredde xml_real64, indreHøyde xml_real64, ytreBredde xml_real64, ytreHøyde xml_real64, indreDiameter xml_real64, ytreDiameter xml_real64, ytreDybde xml_real64
    -> Tunnel
Tunnel: Inspector
Borehull (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, beliggenhet xml_geometry, stedfestingsårsak xml_buffer, stedfestingsforhold xml_buffer, tilKobling.nilReason xml_buffer, tilKobling.gml_remoteSchema xml_buffer,
      tilKobling.xlink_href xml_buffer, tilKobling.xlink_role xml_buffer, tilKobling.xlink_title xml_buffer, tilKobling.owns xml_boolean, fraKobling.nilReason xml_buffer, fraKobling.gml_remoteSchema xml_buffer, fraKobling.xlink_href xml_buffer, fraKobling.xlink_role xml_buffer, fraKobling.xlink_title xml_buffer, fraKobling.owns xml_boolean, stikkledning xml_buffer, bruk{} xml_buffer, indreBredde xml_real64, indreHøyde xml_real64, ytreBredde xml_real64, ytreHøyde xml_real64, indreDiameter xml_real64, ytreDiameter xml_real64
    -> Borehull
Borehull: Inspector

Bookmark: Koblinger
Kum (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, hovedbruk xml_buffer, ytreDiameter xml_real64, posisjon xml_geometry, omriss xml_geometry, ytreHøyde xml_real64
    -> Kum
Kum: Inspector
Tank (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, hovedbruk xml_buffer, ytreDiameter xml_real64, posisjon xml_geometry, omriss xml_geometry, ytreHøyde xml_real64
    -> Tank
Tank: Inspector
Kumlokk (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, senterLokk xml_geometry, identifikasjon.Identifikasjon.lokalId xml_buffer, identifikasjon.Identifikasjon.navnerom xml_buffer, identifikasjon.Identifikasjon.versjonId xml_buffer, rist xml_buffer, kumlokkform xml_buffer, påTank.nilReason xml_buffer, påTank.gml_remoteSchema xml_buffer, påTank.xlink_href xml_buffer, påTank.xlink_role xml_buffer, påTank.xlink_title xml_buffer, påTank.owns xml_boolean, påKum.nilReason xml_buffer, påKum.gml_remoteSchema xml_buffer, påKum.xlink_href xml_buffer, påKum.xlink_role xml_buffer, påKum.xlink_title xml_buffer, påKum.owns xml_boolean
    -> Kumlokk
Kumlokk: Inspector
Nettverkstasjon (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, identifikasjon.Identifikasjon.lokalId xml_buffer, identifikasjon.Identifikasjon.navnerom xml_buffer, identifikasjon.Identifikasjon.versjonId xml_buffer, status xml_buffer, eier{}.Eier.eiertype xml_buffer, eier{}.Eier.eier xml_buffer, eier{}.Eier.eierAndel xml_real64, maks3dAvvik.Maks3dAvvik.maksAvvikVertikalt xml_int64, maks3dAvvik.Maks3dAvvik.maksAvvikHorisontalt xml_int64, vertikalnivå xml_buffer, høydereferanse xml_buffer, foto.nilReason xml_buffer, foto.gml_remoteSchema xml_buffer, foto.xlink_href xml_buffer, foto.xlink_role xml_buffer, foto.xlink_title xml_buffer, foto.owns xml_boolean, hovedbruk xml_buffer, utstrekning{}.Delgeometrier.ytreHøyde xml_real64, utstrekning{}.Delgeometrier.omriss xml_geometry, type xml_buffer
    -> Nettverkstasjon
Nettverkstasjon: Inspector
NettstasjonAdkomst (reader GML_1) [off]
    attributes: datafangstdato xml_date, kvalitet.Posisjonskvalitet.målemetode xml_buffer, kvalitet.Posisjonskvalitet.nøyaktighet xml_int64, kvalitet.Posisjonskvalitet.målemetodeHøyde xml_buffer, kvalitet.Posisjonskvalitet.nøyaktighetHøyde xml_int64, informasjon{} xml_buffer, registreringsversjon.Registreringsversjon.produkt xml_buffer, registreringsversjon.Registreringsversjon.versjon xml_buffer, posisjon xml_geometry, identifikasjon.Identifikasjon.lokalId xml_buffer, identifikasjon.Identifikasjon.navnerom xml_buffer, identifikasjon.Identifikasjon.versjonId xml_buffer, type xml_buffer, nettverkstasjon.nilReason xml_buffer, nettverkstasjon.gml_remoteSchema xml_buffer, nettverkstasjon.xlink_href xml_buffer, nettverkstasjon.xlink_role xml_buffer, nettverkstasjon.xlink_title xml_buffer, nettverkstasjon.owns xml_boolean
    -> NettstasjonAdkomst
NettstasjonAdkomst: Inspector

Bookmark: Ledningseierforskriften testfiler
Skråfoto (reader GML_1) [off]
    attributes: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
