FME workspace Terringmodell.fmw

Parameters:
- GeometrifilterJsonURL =
- SourceDataset_GML =

Readers:
- GML_1: GML from $(SourceDataset_GML)

AnnetVegarealAvgrensning (reader GML_1)
    attributes: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
Fortauskant (reader GML_1)
    attributes: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
GangfeltAvgrensning (reader GML_1)
    attributes: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
GangSykkelveg (reader GML_1)
    attributes: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
GangSykkelvegkant (reader GML_1)
    attributes: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
Gangvegkant (reader GML_1)
    attributes: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
Kjørebanekant (reader GML_1)
    attributes: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
Parkeringsområde (reader GML_1)
    attributes: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
Skiltportal (reader GML_1)
    attributes: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
Trafikksignalpunkt (reader GML_1)
    attributes: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
Trafikkøy (reader GML_1)
    attributes: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
Trafikkøykant (reader GML_1)
    attributes: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
Traktorveg (reader GML_1)
    attributes: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
Traktorvegkant (reader GML_1)
    attributes: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
Veg (reader GML_1)
    attributes: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
Vegdekkekant (reader GML_1)
    attributes: identifikasjon.Identifikasjon.lokalId xml_buffer, identifikasjon.Identifikasjon.navnerom xml_buffer, identifikasjon.Identifikasjon.versjonId xml_buffer, datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry, nedsenketKantstein xml_boolean, høydereferanse xml_buffer, medium xml_buffer
    -> SurfaceModeller [POINTS/LINES]
    -> Vegdekkekant
Vegdekkekant: Inspector
VeggrøftÅpen (reader GML_1)
    attributes: identifikasjon.Identifikasjon.lokalId xml_buffer, identifikasjon.Identifikasjon.navnerom xml_buffer, identifikasjon.Identifikasjon.versjonId xml_buffer, datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry
    -> SurfaceModeller [POINTS/LINES]
    -> VeggrøftÅpen
VeggrøftÅpen: Inspector
VegkantAnnetVegareal (reader GML_1)
    attributes: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
VegkantAvkjørsel (reader GML_1)
    attributes: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
Vegskulderkant (reader GML_1)
    attributes: identifikasjon.Identifikasjon.lokalId xml_buffer, identifikasjon.Identifikasjon.navnerom xml_buffer, identifikasjon.Identifikasjon.versjonId xml_buffer, datafangstdato xml_date, registreringsversjon.Registreringsversjon.produkt xml_buffer, registreringsversjon.Registreringsversjon.versjon xml_buffer, registreringsversjon.Registreringsversjon.undertype xml_buffer, verifiseringsdato xml_date, oppdateringsdato xml_datetime, informasjon xml_buffer, prosesshistorie xml_buffer, kopidata.Kopidata.områdeId xml_int64, kopidata.Kopidata.originalDatavert xml_buffer, kopidata.Kopidata.kopidato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, grense xml_geometry, nedsenketKantstein xml_boolean, høydereferanse xml_buffer, medium xml_buffer
    -> SurfaceModeller [POINTS/LINES]
    -> Vegskulderkant
SurfaceModeller
    ADDZ_TYPE = Replace Z
    CONTOUR_DIMENSION = 3
    CONTOUR_INTERVAL = 100.0
    DRAPE_TYPE = VERTEX
    IGNORE_INPUT_ON_INTERVAL = Perturb Input Points On Contour Interval
    INTERPOLATION_TYPE = AUTO
    NODATA_VALUE = -32767.0
    TOLERANCE = 0.05
    X_SPACING = 100.0
    Y_SPACING = 100.0
    TINSurface -> SurfaceClipper [Clippee]
Vegskulderkant: Inspector
Creator
    GEOMTYPE = Geometry Object
    NUM = 1
    CREATED -> FeatureReader [INITIATOR]
Note: Lillehammer / https://www.norgeskart.no/ws/get-json.py?hash=Oc6JcHkB1BVmjWzlBFjs&save=true / Hamar / https://www.norgeskart.no/ws/get-json.py?hash=f2kaLn0BWQwIHzRH92XD&save=true / Bygland / https://www.norgeskart.no/ws/get-json.py?hash=MbttMn0BAC97_wZzXMDB&save=true
FeatureReader
    ATTRIBUTES = get-json,"id,measurement,style.fill.color,style.stroke.color,style.stroke.width"
    ATTR_ACCUM_MODE = Only Use Result
    COMBINE_GEOM = Use Result
    DATASET = https://www.norgeskart.no/ws/get-json.py?hash=f2kaLn0BWQwIHzRH92XD&save=true
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> Reprojector
Reprojector
    DEST = EPSG:25832
    INTERPOLATION_TYPE_NAME = Nearest Neighbor
    RASTER_CELL_SIZE = Preserve Cells
    RASTER_TOLERANCE = 0.0
    SOURCE = EPSG:4326
    REPROJECTED -> SurfaceClipper [Clipper]
SurfaceClipper
    Inside -> SurfaceClipper_Inside
SurfaceClipper_Inside: Inspector
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> FaceReplacer [off]
    INSIDE -> Clipper_Inside
FaceReplacer
    ANGULAR_TOLERANCE_CHOICE = Automatic
    THICKNESS_TOLERANCE_CHOICE = Automatic
    -> SurfaceModeller_TINSurface
SurfaceModeller_TINSurface: Inspector
Clipper_Inside: Inspector

FME custom transformer SurfaceClipper
The SurfaceClipper will clip a surface or mesh by a 2D polygon boundary. The clip is performed from a 2D top-down perspective, so best results will obtained from mostly horizontal surfaces. Any textures on the surface will be retained.
The transformer will retain the aggregate hierarchies of the incoming features.
Input Ports:
Clipper: This should be a 2D polygon
Clippee: The surface to be clipped. Multi-level hierarchies of surfaces and meshes are acceptable, and the transformer will retain this hierarchy on the output features.

Clipper (input)
    -> GeometryFilter_2
GeometryFilter_2
    BREAK_AGG = No
    GEOM_PORT_NAMES = Area
    AREA -> Junction
    <UNFILTERED> -> AttributeCreator_4
Junction
    -> Clipper [CLIPPER]
Note: Set rejection code
AttributeCreator_4
    ATTR_TABLE = SET_TO fme_rejection_code = INVALID_CLIPPER_GEOMETRY
    -> Junction_9
Clippee (input)
    -> GeometryFilter
Note: Accept only surface
GeometryFilter
    BREAK_AGG = No
    GEOM_PORT_NAMES = Surface
    SURFACE -> AggregateFilter
    <UNFILTERED> -> AttributeCreator
Note: Break up any aggregates, / storing hierarchy
AggregateFilter
    AGGREGATE -> Deaggregator_2
    NOT_AGGREGATE -> GeometryCoercer_2
Deaggregator_2
    COPY_ATTR = Every Node
    EXPLODE_INSTANCES = Yes
    ID_ATTR = _hierarchy_id
    ID_SELECTION = ID and Parent ID
    LIST_ATTR_MODE_LOOKUP = LEAN
    MODE = Preserve Hierarchy
    PARENT_ID_ATTR = _hierarchy_parent_id
    SPLIT_COMPOSITES = No
    DEAGGREGATED -> AggregateFilter_2
Note: Reroute intermediate geometries to rebuild aggregate hierarchy
AggregateFilter_2
    AGGREGATE -> Junction_11
    NOT_AGGREGATE -> GeometryCoercer_2
Junction_11
    -> Junction_12
Junction_12
    -> Aggregator_2
    -> Aggregator_3
Note: Convert meshes/solids to composite surfaces
GeometryCoercer_2
    GQUERY:
      for $geom in //geometry
      where $geom/@fme_geometry_type = 'IFMEMesh'
      return number($geom/@fme_id)
    KIND = fme_composite_surface
    COERCED -> AttributeCreator_5
    UNTOUCHED -> Deaggregator
Note: Store mesh status
AttributeCreator_5
    ATTR_TABLE = SET_TO _set_mesh = yes
    -> Deaggregator
Note: Break up composites into faces
Deaggregator
    EXPLODE_INSTANCES = Yes
    LIST_ATTR_MODE_LOOKUP = LEAN
    MODE = Flatten All Levels
    SPLIT_COMPOSITES = Yes
    DEAGGREGATED -> GeometryExtractor
Note: Store geometry
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> SharedItemIDExtractor
    <REJECTED> -> Junction_6
Note: Get shared item id of appearance
SharedItemIDExtractor
    REFERENCE_ATTRIBUTE = _shared_item_id
    SHARED_TYPE = Appearance
    SIDE_TO_EXTRACT = Front and Back Sides
    STORAGE_MODE = Attribute
    -> AppearanceExtractor_2
    UNMATCHED -> AppearanceExtractor_2
    <REJECTED> -> Junction_7
Note: Extract front texture parameters
AppearanceExtractor_2
    ACCUM_ATTRS = Yes
    ACCUM_TRAITS = Yes
    SIDE_TO_EXTRACT = Front Side
    UNIQUE_STYLES = No
    APPEARANCE -> AttributeExposer
    UNMATCHED -> AppearanceExtractor_3
    UNUSED -> AppearanceExtractor_3
AttributeExposer
    ATTR_LIST = fme_appearance_texture_gen_info
    -> AttributeRenamer
AttributeRenamer
    ATTR_TABLE = RENAME_SET_DEFAULT fme_appearance_texture_gen_info > _front_gen_info
    -> AppearanceExtractor_3
Note: Extract back texture parameters
AppearanceExtractor_3
    ACCUM_ATTRS = Yes
    ACCUM_TRAITS = Yes
    SIDE_TO_EXTRACT = Back Side
    UNIQUE_STYLES = No
    APPEARANCE -> AttributeExposer_2
    UNMATCHED -> GeometryReplacer
    UNUSED -> GeometryReplacer
AttributeExposer_2
    ATTR_LIST = fme_appearance_texture_gen_info
    -> AttributeRenamer_2
Note: No textures
AttributeRenamer_2
    ATTR_TABLE = RENAME_SET_DEFAULT fme_appearance_texture_gen_info > _back_gen_info
    -> GeometryReplacer
Junction_7
    -> Junction_8
Junction_8
    -> GeometryReplacer
Note: Restore geometry
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> GeometryCoercer
    <REJECTED> -> Junction_4
Note: Coerce faces to polygons
GeometryCoercer
    GQUERY:
      for $geom in //geometry
      where $geom/count(parent::geometry) = 0
      return number($geom/@fme_id)
    KIND = fme_polygon
    COERCED -> OrientationExtractor
    UNTOUCHED -> OrientationExtractor
Note: Store original orientation
OrientationExtractor
    ORIENTATION = _orientation
    -> Clipper [CLIPPEE]
Note: Clip polygon
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeCreator_2
    OUTSIDE -> AttributeCreator_3
    <REJECTED> -> Junction_3
Note: Store clipper output
AttributeCreator_2
    ATTR_TABLE = SET_TO _clipper_output = Inside
    -> TestFilter
AttributeCreator_3
    ATTR_TABLE = SET_TO _clipper_output = Outside
    -> TestFilter
Note: Break up clipper aggregates
Deaggregator_3
    ATTR_ACCUM_MODE = Merge List Attributes
    ATTR_CONFLICT_RES = Use List Attribute Values
    EXPLODE_INSTANCES = No
    LIST_ATTR_MODE_LOOKUP = LEAN
    MODE = Flatten One Level
    SPLIT_COMPOSITES = No
    DEAGGREGATED -> FaceReplacer
Note: Convert clipped polygon to face
FaceReplacer
    ANGULAR_TOLERANCE_CHOICE = Ignore
    THICKNESS_TOLERANCE_CHOICE = Ignore
    -> Tester
    <REJECTED> -> Junction_2
Note: Rebuild composite surface for triangulation
Aggregator
    ACCUM_ATTRS_NAME = Use Attributes From One Feature
    AGGREGATE_TYPE = Homogeneous Collection (If Possible)
    GROUP_BY = _hierarchy_id _clipper_output
    MODE = Geometry - Assemble One Level
    SEP = ,
    AGGREGATE -> GeometryRefiner
GeometryRefiner
    -> GeometryCoercer_3
GeometryCoercer_3
    GQUERY:
      for $geom in //geometry
      where $geom/@fme_geometry_type = 'IFMEMultiSurface'
      return number($geom/@fme_id)
    KIND = fme_composite_surface
    COERCED -> Tester_3
    UNTOUCHED -> Tester_3
Note: Triangulate if originally a mesh
Tester_3
    BOOL_OP = OR
    COMPOSITE_TEST = 1
    TEST_CLAUSE = TEST @Value(_set_mesh) = yes
    TEST_MODE = TEST
    PASSED -> Triangulator
    FAILED -> AttributeFilter
Triangulator
    DEAGGREGATE_INPUT = Deaggregate
    TIN_SURFACE -> AttributeFilter
Note: Separate inside and outside outputs
AttributeFilter
    ATTR_NAME = _clipper_output
    ATTR_VALUES = <Empty>,<Missing>,<Null>,<Unfiltered>,Inside,Outside
    Inside -> Aggregator_2
    Outside -> Aggregator_3
Note: Rebuild aggregate hierarchies
Aggregator_2
    AGGREGATE_TYPE = Homogeneous Collection (If Possible)
    ATTR_TO_TRAIT = Yes
    ID_ATTR = _hierarchy_id
    ID_SELECTION = ID and Parent ID
    MODE = Geometry - Assemble Hierarchy
    PARENT_ID_ATTR = _hierarchy_parent_id
    PRESERVE_ID = No
    AGGREGATE -> Inside (output)
Inside (output)
Aggregator_3
    AGGREGATE_TYPE = Homogeneous Collection (If Possible)
    ATTR_TO_TRAIT = Yes
    ID_ATTR = _hierarchy_id
    ID_SELECTION = ID and Parent ID
    MODE = Geometry - Assemble Hierarchy
    PARENT_ID_ATTR = _hierarchy_parent_id
    PRESERVE_ID = No
    AGGREGATE -> Outside (output)
Outside (output)
Note: Set rejection code
AttributeCreator
    ATTR_TABLE = SET_TO fme_rejection_code = INVALID_GEOMETRY
    -> Junction_9
Junction_9
    -> Junction_6
Junction_6
    -> Junction_4
Junction_4
    -> Junction_3
Junction_3
    -> Junction_13
Junction_13
    -> Junction_2
Junction_2
    -> Junction_5
Junction_5
    -> Junction_10
Junction_10
    -> <Rejected> (output)
<Rejected> (output)

Bookmark: Fix polygon orientation reversed by Clipper
TestFilter
    DEFAULT_VALUE = <UNFILTERED>
    TEST_LIST = "BOOL_OP,OR,COMPOSITE_TEST,""""""1"""""",TEST_CLAUSE,TEST @Value(_orientation) = left_hand_rule",left_hand_rule,"BOOL_OP,OR,COMPOSITE_TEST,""""""1"""""",TEST_CLAUSE,TEST @Value(_orientation) = right_hand_rule",right_hand_rule
    left_hand_rule -> Orientor
    right_hand_rule -> Orientor_2
Orientor
    KIND = LEFT_HAND_RULE
    ORIENTED -> Deaggregator_3
    <REJECTED> -> Junction_13
Orientor_2
    KIND = RIGHT_HAND_RULE
    ORIENTED -> Deaggregator_3
    <REJECTED> -> Junction_13

Bookmark: Restore front and back textures
Note: The texture generation parameters are used to create new texture coordinates from modified vertices
Tester
    BOOL_OP = OR
    COMPOSITE_TEST = 1
    TEST_CLAUSE = TEST _shared_item_id.front{0} ATTRIBUTE_HAS_A_VALUE ""
    TEST_MODE = TEST
    PASSED -> AttributeRenamer_3
    FAILED -> Tester_2
AttributeRenamer_3
    ATTR_TABLE = RENAME_SET_DEFAULT _front_gen_info > fme_appearance_texture_gen_info
    -> SharedItemIDSetter_2
SharedItemIDSetter_2
    REFERENCE_ATTRIBUTE = _shared_item_id.front{0}
    SHARED_TYPE = Appearance
    SIDE_TO_SET = Front Side
    STORAGE_MODE = From Attribute
    TEXTURE_MAPPING_TYPE_CHOICE = From Texture Coordinate Generation Parameters Attribute
    USE_EXISTING_TEXTURE_COORDINATES = No
    -> Tester_2
    UNMATCHED -> Tester_2
    <REJECTED> -> Junction_5
Tester_2
    BOOL_OP = OR
    COMPOSITE_TEST = 1
    TEST_CLAUSE = TEST _shared_item_id.back{0} ATTRIBUTE_HAS_A_VALUE ""
    TEST_MODE = TEST
    PASSED -> AttributeRenamer_4
    FAILED -> Aggregator
AttributeRenamer_4
    ATTR_TABLE = RENAME_SET_DEFAULT _back_gen_info > fme_appearance_texture_gen_info
    -> SharedItemIDSetter_3
SharedItemIDSetter_3
    REFERENCE_ATTRIBUTE = _shared_item_id.back{0}
    SHARED_TYPE = Appearance
    SIDE_TO_SET = Back Side
    STORAGE_MODE = From Attribute
    TEXTURE_MAPPING_TYPE_CHOICE = From Texture Coordinate Generation Parameters Attribute
    USE_EXISTING_TEXTURE_COORDINATES = No
    -> Aggregator
    UNMATCHED -> Aggregator
    <REJECTED> -> Junction_10
